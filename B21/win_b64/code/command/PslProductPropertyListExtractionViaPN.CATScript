'===============================================================================
' PslMajorEquipmentListPropertyExtractory.CATScript
'
' This VBScript macros is designed to extract a part's property from an Excel
' MEL DataBase .
'===============================================================================
' Author : Sudhi Gulur
' Date   : Sept 2000
' Version: V5R5
'
'===============================================================================
' Before you run this macro, make sure....
' (A) The Major Equipment List Location (strGOriginalMELLocation) is set to the
'     right location and is a valid file.
' (B) The Excel Sheet Name (strGReportEXCELSheetName) is valid.
'
' Step to run this macro:
' (1) Launch CATIA with your model.
' (2) Select the Products for which you want to extract the MEL Data
' (3) Choose this macro from Tools->Macro and execute by selecting Run
'================================================================================

Option Explicit

'******************************************************************************
'  GLOBAL variable declarations section
'******************************************************************************
'// ---------- Debug Traces
Const intG_TRACEON = 1
Dim strMessage

'//---------- EXCEL application 
Dim objGEXCELapp As Object
Dim objGEXCELwkBks As Object
Dim objGEXCELwkBk As Object
Dim objGEXCELwkShs As Object
Dim objGEXCELSh As Object
Dim intNBUsedRow As Integer
Dim intNBUsedColumn As Integer

'// VBScript Objects
Dim FileSysObj, FileObj, SourceFile, DestFile

'// ---------- CATIAV5 application objects
Dim objCATIAV5Document0 As Document
Dim objCATIAV5ArrWorkbench0 As Workbench
Dim objCATIAV5Selection As Selection

Dim objSelProduct As Product

Dim intGReportCurrentRow  
Dim intGReportMaxColumnIndex
Dim dblGTotalLength


Const intColumnTitleRowNumber = 4

'========== EXCEL template direction path
Const strGOriginalMELLocation = "C:\temp\MajorEquipmentList.xls" 

'---------- must name the sheet in the template accordingly
Const strGReportEXCELSheetName = "Reference Item List"

'----------OUTPUT HTML File Name
Const strGOutputHTMLFileName = "c:\temp\Property.html"

'----------OUTPUT TEMP DIRECTORY
Const strGOutputDirName = "C:\Temp"

'@@@@@@@@@@@@@@@@@@@@@@@@@@@@@@@@@@@@@@@@@@@@@@@@@@@@@@@@@@@@@@@@@@@@@@@@@@@@@@

'******************************************************************************
Sub DbgTrace (iStrMsgString, iIntYesError)
'******************************************************************************
If (intG_TRACEON = 1) Then
  CATIA.SystemService.Print iStrMsgString 
  If (iIntYesError = 1) Then 
	   CATIA.SystemService.Print "Err Number = " & Err.Number
	End If
End If

End Sub '///////////////////////////////////////////////////////////// DbgTrace


'========================================================================
Sub Copy_Files(strFileToCopy)
'========================================================================

 Dim strCATCommandPath           As String
 Dim strNewFilePath              As String
 Dim intSemiColonLocation        As Integer
 Dim strDefaulLocationOfTemplate As String
 Dim AppliFileSys                As FileSystem
   
   On Error Resume Next
   strCATCommandPath = CATIA.SystemService.Environ("CATCommandPath")  
   
   intSemiColonLocation  = Instr(3, strCATCommandPath, ";")  
          
   Set AppliFileSys = CATIA.FileSystem
   strDefaulLocationOfTemplate = ""
   strNewFilePath              = strGOutputDirName + "\" + strFileToCopy
   'CATIA.SystemService.Print strCATCommandPath

   If (intSemiColonLocation > 0) Then    
      Do While (intSemiColonLocation > 0)

        intSemiColonLocation = intSemiColonLocation -1
        strDefaulLocationOfTemplate = Left(strCATCommandPath, intSemiColonLocation) _
                                    + "\" + strFileToCopy

        If (AppliFileSys.FileExists(strDefaulLocationOfTemplate)) Then
          Exit Do 
        End If

        Err.Clear
        intSemiColonLocation =  intSemiColonLocation + 2
        strCATCommandPath = Mid(strCATCommandPath, intSemiColonLocation)
        intSemiColonLocation  = Instr(3, strCATCommandPath, ";")

        'CATIA.SystemService.Print strCATCommandPath
        'DbgTrace "intSemiColonLocation :" & intSemiColonLocation, 0

      Loop     ' Exit outer loop immediately.
   Else
      strDefaulLocationOfTemplate = strCATCommandPath + "\" + strFileToCopy
   End If
  
   AppliFileSys.CopyFile strDefaulLocationOfTemplate, strNewFilePath, true

   If (Not(AppliFileSys.FileExists(strNewFilePath))) Then
     Dim strMessage
     strMessage  = "Error Copying Template File:" + strDefaulLocationOfTemplate + "to " + strGOutputDirName + Chr(13)
     strMessage  = strMessage + Chr(13) + "Check the following...." + Chr(13)
     strMessage  = strMessage + "(1)Template File has read-write capability" + Chr(13)
     strMessage  = strMessage + "(2)Template File path is valid"
     msgbox (strMessage)    
     Exit Sub
   End If

End Sub



'******************************************************************************
Sub StartEXCEL()
'******************************************************************************
  Err.Clear
  On Error Resume Next
  Set objGEXCELapp = GetObject (,"EXCEL.Application")  
  If Err.Number <> 0 Then   
     Err.Clear
     Set objGEXCELapp = CreateObject ("EXCEL.Application")
  End If

  objGEXCELapp.Application.Visible = FALSE

  Copy_Files ("LaunchIE.bat")
  Copy_Files ("PropertyBackground.gif")

  Set objGEXCELwkBks = objGEXCELapp.Application.WorkBooks

  Err.Clear
  Set objGEXCELwkBk = objGEXCELwkBks.Add (strGOriginalMELLocation)
  If Err.Number <> 0 Then
     Dim strMessage
     strMessage  = "Error Loading Template File:" + strGOriginalMELLocation + Chr(13)
     strMessage  = strMessage + Chr(13) + "Check the following...." + Chr(13)
     strMessage  = strMessage + "(1)Template File has read-write capability" + Chr(13)
     strMessage  = strMessage + "(2)Template File path is valid"
	   msgbox (strMessage)
     Err.Clear
  End If
  Set objGEXCELwkShs = objGEXCELwkBk.Worksheets
  Set objGEXCELSh = objGEXCELwkBk.Sheets (strGReportEXCELSheetName)
  objGEXCELSh.Select

  Dim objURange As Range
  Set objURange = objGEXCELSh.UsedRange
  intNBUsedColumn = objURange.Columns.Count

  intNBUsedRow = objURange.Rows.Count
  DbgTrace "Number of Used Columns :" & intNBUsedColumn,0
  DbgTrace "Number of Used Rows    :" & intNBUsedRow,0

End Sub '/////////////////////////////////////////////////////////// StartEXCEL

'******************************************************************************
Sub EndEXCEL ()
'******************************************************************************
  objGEXCELwkBk.Close
  objGEXCELapp.Quit
End Sub '///////////////////////////////////////////////////////////// EndEXCEL

'******************************************************************************
Sub StartCATIAV5 ()
'******************************************************************************
  Set objCATIAV5Document0 = CATIA.ActiveDocument
  DbgTrace "V5: Active Document",1

  '//---------- Get current selection
  Set objCATIAV5Selection = objCATIAV5Document0.Selection
  DbgTrace "V5: Selection",1

End Sub '///////////////////////////////////////////////////////// StartCATIAV5

'******************************************************************************
Sub ProcessProduct(iobjCATIAV5Product)
'******************************************************************************
 
 Dim strProductPartNumber   As String
 Dim strProductInstanceName As String
 Dim strProductDefinition   As String
 Dim intIsThisKBRProduct    As Integer
 Dim intNoObjectWasFound    As Integer
 Dim strSelProductData      As String
 Dim intRequiredRowFound    As Integer
 Dim strMELItemNumber       As String

 strProductPartNumber = iobjCATIAV5Product.PartNumber
 strProductDefinition = iobjCATIAV5Product.Definition

 'MsgBox "Product Definition:" & strProductDefinition
 
 intNoObjectWasFound  = 0
 intIsThisKBRProduct  = 0
 strSelProductData    = ""
 intRequiredRowFound  = 0
 
 If (Len(strProductPartNumber) > 0) Then

   'strMELItemNumber = Left(strProductPartNumber, 6)
    strMELItemNumber  = strProductPartNumber
    DbgTrace strMELItemNumber,0

    Dim intIRow As Integer
     For intIRow = 6 to intNBUsedRow
       Dim strCheckItemName As String
       strCheckItemName = objGEXCELSh.Cells(intIRow, 1).Value
       'If(Instr(1, strCheckItemName, strMELItemNumber)) Then
       If(StrComp(strCheckItemName, strMELItemNumber) = 0) Then
        NoObjectWasFound = 1
        strSelProductData = strSelProductData + "<B><font color=#FFFF00>" + strProductPartNumber + "</font></B>"
        strSelProductData = strSelProductData + "<TABLE BORDER=1 bgcolor=#FFFFFF>"
        strSelProductData = strSelProductData + "<TR><TD BGCOLOR=#60FF60>Property&nbsp;</TD><TD BGCOLOR=#60FF60>Value&nbsp;</TD></TR>"

        FileObj.WriteLine(strSelProductData )

        Dim intIColumn As Integer
         'For intIColumn = 2 to intNBUsedColumn
          For intIColumn = 2 to intNBUsedColumn
           Dim strData        
           Dim strColumnTitle 

           'DbgTrace "Processing Cell:(" & intIRow _
           '& "," & intIColumn & ")", 0

           strColumnTitle = CStr(objGEXCELSh.Cells(4, intIColumn).Value)
           DbgTrace "Title:" & strColumnTitle, 0

           strData        = CStr(objGEXCELSh.Cells(intIRow, intIColumn).Value)
           DbgTrace "Value:" & strData, 0

            strSelProductData = "<TR><TD> " + strColumnTitle + "&nbsp;" _
                              + "</TD><TD>" + strData + "&nbsp;</TD></TR>"

           ' strSelProductData = strSelProductData + "Title:" + strColumnTitle _
           '                     + "Value:" + strData + Chr(10)

           FileObj.WriteLine(strSelProductData )
         
          Next ' intIColumn
      
          strSelProductData = "</TABLE>"
          FileObj.WriteLine(strSelProductData )
          intIRow = intNBUsedRow
       Else

       End If
     Next ' intIRow
 End If

 If (NoObjectWasFound < 1) Then
  DbgTrace Hello,0
  strSelProductData = "<B><font color=#FFFF00>" + strProductPartNumber + " : not found in MEL </font></B>"
  FileObj.WriteLine(strSelProductData )
 End If


 If (Len(strSelProductData) > 0) Then
   'MsgBox strSelProductData
    'FileObj.WriteLine(strSelProductData )
 End If 

End Sub '///////////////////////////////////////////////////////// ProcessProduct

'******************************************************************************
Sub CATMain()
'******************************************************************************

 '//================================================================================
 '//Define the variables needed in the Main program
 '//================================================================================
 
 On Error Resume Next
 '//================================================================================
 '// Execution Starts Here
 '//================================================================================
  intNBUsedRow            = 0
  intNBUsedColumn         = 0
  intGReportCurrentRow    = 5  '// Start on 10th Row after the image area

  StartEXCEL
  StartCATIAV5

  Set FileSysObj = CreateObject("Scripting.FileSystemObject")
  Set FileObj = FileSysObj.CreateTextFile(strGOutputHTMLFileName, True)
  FileObj.WriteLine("<HTML><TITLE>Properties</TITLE><BODY BACKGROUND=PropertyBackground.gif>")

  Err.Clear
  Set objSelProduct = objCATIAV5Selection.FindObject("CATIAProduct")
  DbgTrace "FindObject", 0

  if (Err.Number <> 0) Then 
    Set objSelProduct = Nothing
  Else
    Do Until ( objSelProduct Is Nothing )
       
       ProcessProduct objSelProduct

       Set objSelProduct = objCATIAV5Selection.FindObject("CATIAProduct")
       if (Err.Number <> 0) Then 
          Set objSelProduct = Nothing
          Exit Do
       End If
    Loop  '// End Do ...each FindObject
  End If

  FileObj.WriteLine("</BODY></HTML>")
  FileObj.Close

  Dim strExecString As String
  strExecString = strGOutputDirName + "\LaunchIE.bat" + " " + strGOutputHTMLFileName
  CATIA.SystemService.ExecuteBackgroundProcessus(strExecString)
  
  EndEXCEL

End Sub '////////////////////////////////////////////////////////////// CATMain
