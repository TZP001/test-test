''  ------------------------------------------------------
''   VBScript for Manufacturing Tools catalog generation.
''  ------------------------------------------------------


Language="VBSCRIPT"


'======================
'  Test cession flag
'======================
dim IsaTest as Boolean
IsaTest = False


' ExecutionMode : 0 -> Appel par Tools->Macros
'                 1 -> Appel par menu CATIA
dim ExecutionMode
ExecutionMode = 1

dim FolderSeparator as string

Function GetDefaultWorkingPath

  dim result

  on error resume next
  result = Catia.SystemService.Environ("CATStartupPath")

  if(err.number<>0) then
    Err.Clear
    result = Catia.SystemService.Environ("TEMP")
    dim fso as FileSystem
    set fso = CATIA.FileSystem
    if(NOT fso.FolderExists(result)) then result = ""
    set fso = NOTHING
  else
    if(mid(result,len(result),1)<>FolderSeparator) then result = result & FolderSeparator
    result = result & "Manufacturing"&FolderSeparator&"Tools"
  end if

  if(mid(result,len(result),1)<>FolderSeparator) then result = result & FolderSeparator

  GetDefaultWorkingPath = result

End Function


function TestCSVFileName (FileName)

  dim reponse
  reponse=True

  if (FileName="") then
    MsgBox "Operation canceled"
    reponse=False
  else
    dim fso as FileSystem
    set fso = CATIA.FileSystem
    if(NOT(fso.FileExists(FileName))) then
      MsgBox "Missing csv file : Operation canceled"
      reponse=False
    end if
    set fso = NOTHING
  end if

  TestCSVFileName = reponse

end function


sub CATMain()

'------------------------------------------------------------------
' test Macro Atelier
' creation Juillet2000 :    (kbb)
' lecture d'un modele 
'------------------------------------------------------------------

  dim theStartupDir as String
  theStartupDir = Catia.SystemService.Environ("CATStartupPath")
  posslash = Instr(theStartupDir, "/")

  if(posslash=0) then
    FolderSeparator = "\"  'windows
  else
    FolderSeparator = "/"  'unix
  end if
  
  EnvVar = Catia.SystemService.Environ("ADL_ODT_CATOUT_TEST")
  Catia.SystemService.Print "EnvVar=" & EnvVar

  If ( EnvVar = "PERFORM_CATOUT_TEST" ) Then
    Catia.SystemService.Print "IN MKODT"
    IsaTest = True

    '------------------------------------------------------------------
    Catia.SystemService.Print "Lire le modele"
    AdlOdtTmp = Catia.SystemService.Environ("ADL_ODT_TMP")
    Catia.SystemService.Print "AdlOdtTmp=" & AdlOdtTmp

    Slash = Catia.SystemService.Environ("ADL_ODT_SLASH")
    Catia.SystemService.Print "Slash=" & Slash

    AdlOdtTmpPath = AdlOdtTmp & Slash
    Catia.SystemService.Print "Path=" & AdlOdtTmpPath

  End If


  ExecutionMode = 0

  dim WorkingPath
  dim DefaultcsvFile, DefaultCatalogFile, DefaultCatalogExtension
  dim csvFile, catalogFile


  if(NOT IsaTest) then


    WorkingPath = GetDefaultWorkingPath

    DefaultcsvFile     = WorkingPath & "MyCatalog.csv"
    DefaultCatalogFile = WorkingPath & "MyCatalog.catalog"
    DefaultCatalogExtension = ".catalog"

    csvFile = InputBox("Tool descriptions file","File", DefaultcsvFile)

    if (NOT (TestCSVFileName(csvFile))) then exit sub

    dim namelength, posdernierslash, posdernierpoint, i as integer
    posdernierslash = 0
    posdernierpoint = 0
    namelength = len(csvFile)
  
    dim CurrChar as VARIANT
    for i=1 to namelength
      CurrChar = mid(csvFile,i,1)
      if(CurrChar="\" OR CurrChar="/") then posdernierslash=i
      if(CurrChar=".") then posdernierpoint=i
    next
  
    if(posdernierpoint<=posdernierslash) then
      DefaultCatalogFile = csvFile & DefaultCatalogExtension
    else
      DefaultCatalogFile = mid(csvFile,1,posdernierpoint-1) & DefaultCatalogExtension
    end if

    catalogFile = InputBox("Tool catalog file","File", DefaultCatalogFile)

  else
    csvFile = AdlOdtTmpPath & "MyCatalogVB.csv"
    catalogFile = AdlOdtTmpPath & "MyCatalogVB.catalog"
  end if

  CATCsvToCatalog csvFile , catalogFile

end sub


sub CATCsvToCatalog(csvFile, catalogFile)

  if (catalogFile="") then
   MsgBox "Operation canceled"
   Exit sub
  end if

  dim fso as FileSystem
  set fso = CATIA.FileSystem

  if(fso.FileExists(catalogFile)) then

    if(NOT IsaTest) then
      dim DeleteDirPrompt
      DeleteDirPrompt = catalogFile & " already exists" & Chr(13) & "Do you want to replace it?"
      reponse = MsgBox (DeleteDirPrompt,4100,"Replace file?")
      if (reponse=vbYes) then
        fso.DeleteFile(catalogFile)
      else
        MsgBox "Operation canceled"
        Exit sub
      end if
    else
      fso.DeleteFile(catalogFile)
    end if
  end if
  set fso = NOTHING


 'Creates a catalog document

  dim Catlg As Document

  set Catlg = CATIA.Documents.Add("CatalogDocument")

  Catlg.CreateCatalogFromcsv csvFile , catalogFile

  Catlg.Close

end sub
