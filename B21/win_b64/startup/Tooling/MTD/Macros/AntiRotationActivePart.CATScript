Language="VBSCRIPT"



Set settingControllers1 = CATIA.SettingControllers
Set knowledgeSheetSettingAtt1 = settingControllers1.Item("CATLieKnowledgeSheetSettingCtrl")

knowledgeSheetSettingAtt1.RelationsUpdateInPartContextSynchronousRelations = 1
knowledgeSheetSettingAtt1.RelationsUpdateInPartContextEvaluateDuringUpdate = 1




Sub CATMain()


dim oneline as string
dim blankLine as string
dim doubleLine as string
dim title1 as string

IconeInterdit = 16
IconeQuestion = 32
IconeExclamation = 48
IconeInfo = 64

oneline = chr(13)
blankline = chr(13)&chr(13)
doubleline = chr(13)&chr(13)&chr(13)

Ikeep = 1
 
Ititle = "Creation of AntiRotation Test for Splitable Component"
msg1 = "Component                   =  Main PartBody of active CATPart"&oneline
msg2 = "Component orientation = Splitable portion toward Z+"&oneline
msg3 = "Component origin          = Base  in geometric set named  BaseBody"&blankline
msg4 = "You will be asked for the name of parameter defining the diameter of the splitable portion of the component"&blankline
msg5 =  "If your component satisfies these conventions : OK"&oneline
msg6 =  "Otherwise you must prepare it : CANCEL "&oneline

myreturn = msgbox (msg1 & msg2 &msg3 & msg4 & msg5&msg6, IconeQUESTION+1 ,ITitle )
	if ( Myreturn =1 ) then
		IKeep = 1
	else
         IKeep = 0
    end if

'------------------------------------TEST RECEIVINg PART -----------------------------------------



if  ( Ikeep =1 )then
On error resume next
Err.clear
Dim documents1 As Documents
Set documents1 = CATIA.Documents

Dim partDocument1 As Document
Set partDocument1 = Catia.ActiveDocument
if ( Err<>0) then
    Ikeep =0
    MsgBox "Error : No active CATPart"
end if
end if 


'--  Creation of the Knowledge parameter 
if  ( Ikeep =1 )then

On error resume next
Err.clear
Dim part1 As Part
Set part1 = partDocument1.Part
Set parameters1 = part1.Parameters
Set relations1 = part1.Relations

Set settingControllers1 = CATIA.SettingControllers
Set knowledgeSheetSettingAtt1 = settingControllers1.Item("CATLieKnowledgeSheetSettingCtrl")

JTitle = "Creation of synchronous rules"
msgA= "Do you accept modification of settings : Tools/Options/Parameters and Measures/Knowledge/RelationsUpdateInPartContext ?"
myreturn = msgbox (msgA , IconeQUESTION+1 ,JTitle )
	if ( Myreturn =1 ) then
         IMsgRule=0
		knowledgeSheetSettingAtt1.RelationsUpdateInPartContextSynchronousRelations = 1
        knowledgeSheetSettingAtt1.RelationsUpdateInPartContextEvaluateDuringUpdate = 1
	else
         IMsgRule=1
         msgB= "It is recommanded to edit the properties of the rule AntiRotationTest to make sure it is updated with the part"

    end if



Set strParam1 = parameters1.Item("AntiRotation")
if ( Err=0) then
    Ikeep =0
    MsgBox "Error : there is already a parameter named ""AntiRotation"" in the CATPart"
end if
err.clear
end if

if  ( Ikeep =1 )then

Set rule1 = relations1.Item("AntiRotationTest")
if ( Err=0) then
    Ikeep =0
    MsgBox "Error : there is already a rule named ""AntiRotationTest"" in the CATPart"
end if
err.clear
end if

if  ( Ikeep =1 )then

'  BaseBody becomes currenT
'---------------------------------------------
Set hybridShapeFactory1 = part1.HybridShapeFactory
Set hybridBodies1 = part1.HybridBodies
Set hybridBody1 = hybridBodies1.Item("BaseBody")
if ( Err<>0) then
    Ikeep =0
    MsgBox "Error : No Geometric set BaseBody"
end if
end if 

'-- Base is used

if ( Ikeep =1 ) then
Set hybridShapes1 = hybridBody1.HybridShapes
Set hybridShapeBASE = hybridShapes1.Item("Base")
if ( Err<>0) then
    Ikeep =0
    MsgBox "Error : No point Base"
end if
end if

if ( Ikeep =1 ) then
Set referenceBASE = part1.CreateReferenceFromObject(hybridShapeBASE)
Part1.InWorkObject =hybridShapeBASE
Part1.Update
if ( Err<>0) then
    Ikeep =0
    MsgBox "Error : Part not Up to Date"
end if
end if


if ( Ikeep =1 ) then
Set hybridBodyBB = hybridBodies1.Item("BaseBody")
Set hybridShapesBB = hybridBodyBB.HybridShapes
ILast =hybridShapesBB.Count
Set hybridShapeBB = hybridShapesBB.Item(Ilast)
LastName=  Left(hybridShapeBB.Name,18)
if (LastName="AxialHighestPoint." ) then
    Ikeep =0
    MsgBox "Error : there is already a feature named AxialHighestPoint in BaseBody"
end if
end if

'------------------------------------TEST UDF -----------------------------------------


if  ( Ikeep =1 )then

'--Search of a User Feature Reference "AxialHighestPoint" 
'------------------------------------------------------------------



' This user feature is stored in the FromDir
FromDir = CATIA.SystemService.Environ("CATStartupPath")&"\Tooling\MTD\UDF\"
StartPartPath=FromDir&"AxialHighestPointsUDF.CATPart"
CATIA.DisplayFileAlerts = False
Set PartDocumentStart = CATIA.Documents.Read (StartPartPath)
Set PartStart = PartDocumentStart.Part
Dim reference As Object
Set reference = PartStart.FindObjectByName("AxialHighestPoint" )
if ( Err<>0) then
    Err.clear
    MsgBox "Ressource problem with "&StartPartPath
    ITitle = "Define UDF Path"
    IPrompt="Enter AxialHighestPointUDF path"
    FromDir = InputBox ( IPrompt, ITitle , FromDir)
    StartPartPath=FromDir&"AxialHighestPointsUDF.CATPart"
    CATIA.DisplayFileAlerts = False
    Set PartDocumentStart = CATIA.Documents.Read (StartPartPath)
    Set PartStart = PartDocumentStart.Part
    Set reference = PartStart.FindObjectByName("AxialHighestPoint" )
     if ( Err<>0) then
          IKeep=0
     end if
end if







end if 

'------------------------------------ENTER INPUTS -----------------------------------------

if  ( Ikeep =1 )then
AntiRotationTolerance = -1.

ITitle = "Define Anti Rotation Tolerance"
IPrompt="Enter minimum Z variation for top face : above this value, antirotation is needed"
AntiRotationTolerance = InputBox ( IPrompt, ITitle , 0.01)
if (AntiRotationTolerance=0.) then
   Ikeep=0
else
   Ikeep =1
end if
end if



if  ( Ikeep =1 )then
 

ITitle = "Define Name of Component Diameter "
IPrompt="Enter the name of the diameter of the Component splitable portion"
ComponentDiameter="xx"
ComponentDiameter = InputBox ( IPrompt, ITitle , "D")
if (ComponentDiameter="") then
   Ikeep=0
else
   Ikeep =1
end if
end if


if  ( Ikeep =1 )then

'  Creation of AntiRotation parameter and its two values
'-----------------------------------------------------------------------------

Set strParam1 = parameters1.CreateString( "", " ")
strParam1.Rename "AntiRotation"
Dim arrayOfVariantOfBSTR1(1)
arrayOfVariantOfBSTR1(0) = "NotNeeded"
arrayOfVariantOfBSTR1(1) = "Needed"
strParam1.SetEnumerateValues arrayOfVariantOfBSTR1
strParam1.Value = "Needed"
'-----------------------------------------------------------------------------

end if 


'------------------------------------Instantiate UDF -----------------------------------------


' Instanciation of a User Feature Reference "AxialHighestPoint" 
'------------------------------------------------------------------
if ( Ikeep =1 ) then

' There are
' 5 inputs: PartBody, xy plane, YZ plane, ZX plane, Base
' 1 published input  parameters: TOPRadius
' 3 output: AxialHighestPoint,TopLowestPoint, TopHighestPoint


Set factory = Part1.GetCustomerFactory("InstanceFactory")
Set instance = factory.AddInstance(reference)

'------------------------------------------------------------------
Set PartBody = Part1.FindObjectByName("PartBody")
Set xyplane = Part1.FindObjectByName("xy plane")
Set yzplane = Part1.FindObjectByName("yz plane")
Set zxplane = Part1.FindObjectByName("zx plane")
Set base = Part1.FindObjectByName("Base")

'------------------------------------------------------------------
instance.PutInput "PartBody", PartBody
instance.PutInput "xy plane", xyplane
instance.PutInput "yz plane", yzplane
instance.PutInput "zx plane", zxplane
instance.PutInput "Base", Base
'------------------------------------------------------------------
set paramII = instance.getparameter("TopRadius")
FormulaContent=ComponentDiameter&"/2"
Set formula1 = relations1.CreateFormula("Formula.17", "", paramII, FormulaContent)
formula1.Rename "FormulaTopRadius"
part1.update
'------------------------------------------------------------------


Set hybridBodyBB = hybridBodies1.Item("BaseBody")
Set hybridShapesBB = hybridBodyBB.HybridShapes
ILast =hybridShapesBB.Count
Set hybridShapeBB = hybridShapesBB.Item(Ilast)
UDFFullName=  "BaseBody\"&hybridShapeBB.Name

'------------------------------------Create Rule -----------------------------------------


'------------------------------------------------------------------

Set outputTopHighestPoint = instance.GetOutput("TopHighestPoint")
Set outputTopLowestPoint = instance.GetOutput("TopLowestPoint")
HighPtName=outputTopHighestPoint.name
LowPtName=outputTopLowestPoint.name
HighZ=HighPtName&" -> coord(3)"
LowZ=LowPtName&" -> coord(3)"
'------------------------------------------------------------------
UDFName =  UDFFullName&"\"
TextHigh=UDFName&HighZ
TextLow =UDFName&LowZ
TextIF = "if ( ("&TextHigh&" - " &TextLow&") >= "&AntiRotationTolerance&"mm"&")"

 ' creation of Antirotation Rule
'--------------------------------------------------------------------------------

Dim rule1 As Rule

RuleHead= "/*AntiRotation Test : Rule created by MTD 4/21/2009*/" 
RuleText = " "
RuleText = RuleText & vbCrLf & textIF
RuleText = RuleText & vbCrLf &"{"
RuleText = RuleText & vbCrLf&"	"&UDFFullName&".Show = true"
RuleText = RuleText & vbCrLf&"	"&UDFName&HighPtName&".Show = true"
RuleText = RuleText & vbCrLf&"	"&UDFName&LowPtName&".Show = true"
RuleText = RuleText & vbCrLf &	"AntiRotation = ""Needed"""
RuleText = RuleText & vbCrLf &"}"
RuleText = RuleText & vbCrLf &"else"
RuleText = RuleText & vbCrLf &"{"
RuleText = RuleText & vbCrLf&"	"&UDFFullName&".Show = false"
RuleText = RuleText & vbCrLf&"	"&UDFName&HighPtName&".Show = false"
RuleText = RuleText & vbCrLf&"	"&UDFName&LowPtName&".Show = false"
RuleText = RuleText & vbCrLf &	"AntiRotation = ""NotNeeded"""
RuleText = RuleText & vbCrLf &"}"

Err.clear
Set rule1 = relations1.CreateProgram("AntiRotationTest",RuleHead, RuleText)
if ( Err<>0) then
    Ikeep =0
    MsgBox "KWA licence needed to create the rule"
else

    rule1.Rename "AntiRotationTest"
    part1.UpdateObject Rule1
    rule1.hidden ="True"
    if ( IMsgRule=1) then
         msgB= "It is recommanded to edit the properties of the rule AntiRotationTest to make sure it is updated with the part"
         myreturn = msgbox (msgB , IconeINFO ,JTitle )
    end if
end if

end if

end sub
