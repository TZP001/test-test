''''''''''''''''''''''''''''''''''''''''''''''''''''''''''''''''''''''''''''
''  Abstract:
''  ---------
''   VBScript for Manufacturing Tools catalog generation.
''
''   1.Create a xls and csv file containing the values you want to store on the Tools
''	   (Example : see MyCatalog.xls and MyCatalog.csv in Samples directory)
''    
''   1.Customize the name of the csv file and the name of the catalog file
''     according to the input and output files you want to use (or use the default names)
''
''   2.Customize the Startup location path according to the software instrallation directory
''     (example : C:\CATIAV5\intel_a\startup)  
''
''   3.Execute this macro with CATIAV5 + Tools + Macro + Macros...    
''
''
'' ''''''''''''''''''''''''''''''''''''''''''''''''''''''''''''''''''''''''''''

Language="VBSCRIPT"

Sub CATMain()


' To remember [ if then else ] programmation in VBScript language

 
 csvFile ="MyCatalog.csv"
 catalogFile ="MyCatalog.catalog"

 'Get the outputDir and inputDir environment variables
  
 manufStr = "Manufacturing"
 samples = "Samples"
 tools   = "Tools"

 startup = "...\intel_a\startup"
 inputDir  = startup & "\" & manufStr & "\" & samples
 outputDir = startup & "\" & manufStr & "\" & tools
 

'Creates a catalog document
 Dim Catlg As Document
 Set Catlg=CATIA.Documents.Add("CatalogDocument")


 InitData1=inputDir & "\" & csvFile
 Newcata1=outputDir & "\" & catalogFile
 
'Calls CreateCatalogFromcsv method on Catlg (ENDCHAPTER)

Catlg.CreateCatalogFromcsv InitData1 , Newcata1 

Catlg.Close

End Sub
