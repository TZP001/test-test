Language="VBSCRIPT"

Sub CATMain()

err.clear
On Error Resume Next

'*********************************************************************
' This macro needs an input file named ListOfCmp that contains the list of components to test.
' two action are done:
' 1. publish every body containing the string DrillHole
' 2. publish in the Body named BaseBody the point named Base
' Please, the following path of files can be modified to meet your requirements.
' ------------------------------------------------------------------------------

	ListOfCmpFile = "E:\ListOfCmp.txt"	' for the input file
	ReportFile = "E:\ReportPublishBodyAndPoint.txt"	' for report file 
'**********************************************************************

' ListOfCmp.txt = file that contains the path of all components (CATPart) to test
' -------------------------------------------------------------------------------
Dim filesys, MyCmp
Set filesys = CreateObject("Scripting.FileSystemObject") 
Set MyCmp = filesys.OpenTextFile(ListOfCmpFile)
If (Err <> 0) Then
	Msg = "The file: " &ListOfCmpFile  & " of components to test does not exist"
	MsgBox Msg
	On Error Goto 0
Else

' ReportFile.txt = file that contains the results 
' -------------------------------------------------------
	Dim filesysHS, textHS
	Set filesysHS = CreateObject("Scripting.FileSystemObject") 
	Set textHS = filesys.CreateTextFile(ReportFile , True)

	Dim encore
	encore = true


'' The macro start !!!
	do while (encore)
		CmpRead = MyCmp.AtEndOfStream
		if (CmpRead) then
			encore = false
		else
			CmpRead = MyCmp.ReadLine
			textHS.WriteLine "Component: " & CmpRead			
			ProcessPublish textHS, CmpRead
		end if
	loop

	MyCmp.Close
	if (tstHS) then textHS.Close
	MsgBox "We hope you enjoy the results !!!"
End If

End Sub


'----------------------------------------------------------------------------------------
' Sub to Publish
'----------------------------------------------------------------------------------------
Sub ProcessPublish ( text, CmpFile )

NbErrors = 0

err.clear
On Error Resume Next

Dim documents1 As Documents
Set documents1 = CATIA.Documents

Dim partDocument1 As Document
Set partDocument1 = documents1.Open(CmpFile)
If (Err <> 0) Then
	text.writeline "ERROR: the file: " &CmpFile  & " does not exist"
	NbErrors = NbErrors + 1
	On Error Goto 0
Else
	' Activate the selection in the document
	Set selection1 = partDocument1.Selection

	' get the product which is included in the document (called rootProduct)
	Dim rootProduct1 As Product
	Set rootProduct1 = partDocument1.Product

	PublishBody text, "DrillHole", selection1 , rootProduct1
	PublishPoint text, "Base", selection1 , rootProduct1

	'Save the CATPart
	err.clear
	partDocument1.Save

	' error management
	if (err <> 0) then
		text.writeline "ERROR: the file: " &CmpFile  & " is write protected"
		err.clear
	end if 

	'Close the CATPart
	partDocument1.Close

End If
text.WriteLine " "
End Sub

'----------------------------------------------------------------------------------------
' Sub to PublishBody
'----------------------------------------------------------------------------------------
Sub PublishBody (text, strName, selection, rootProduct)

	' Search if there is a body called "*strName*" in the document
	selection.Clear
    	str="Name=*"&strName&"*&'Part Design'.Body,all"
	selection.Search(str)
	nbBody = selection.Count

	If (nbBody <> 0) Then 
		nb=0
		for kk = 1 to nbBody
			'Get the complete name of the selected feature (exemple: *DrillHole* --> MyDrillHoleToMe)
			Set feature=selection.Item(kk).Value
			strComplete = feature.Name

			' Publication of the DrillHole body
			str = rootProduct.name &"/!"&strComplete
			Set reference1 = rootProduct.CreateReferenceFromName(str)
			Set publications1 = rootProduct.Publications
		
			'Search if the publication already exists
			nbPub = publications1.count
			jj=0
			for ii = 1 to nbPub
				if (publications1.Item(ii).Name = strComplete) then
					jj = 1 
				end if
			next

			'If the publication exists remove it then create a new one.
			'If the publication doesn't exist create a new one.
			if (jj = 1) then
				publications1.Remove(strComplete)
			end if
			Set publication1 = publications1.Add(strComplete)
			publications1.SetDirect strComplete, reference1
			text.writeline "publish :" &strComplete 

		Next
	Else
		text.writeline "No body with " &strName & " in the name to publish"
	End if

End Sub

'----------------------------------------------------------------------------------------
' Sub to PublishPoint
'----------------------------------------------------------------------------------------
Sub PublishPoint (text, strName, selection, rootProduct)

	' Search if there is a point called "strName" in the document
	selection.Clear
    	str="Name="&strName&"&'Part Design'.Point,all"
	selection.Search(str)
	nbpoint = selection.Count

	If (nbpoint <> 0) Then 
		nb=0
		for kk = 1 to nbpoint
			'Get the complete name of the selected feature 
			Set feature=selection.Item(kk).Value
			strComplete = feature.Name

			' Publication of the Point
			str = rootProduct.name &"/!"&strComplete
			Set reference1 = rootProduct.CreateReferenceFromName(str)
			Set publications1 = rootProduct.Publications
		
			'Search if the publication already exists
			nbPub = publications1.count
			jj=0
			for ii = 1 to nbPub
				if (publications1.Item(ii).Name = strComplete) then
					jj = 1 
				end if
			next

			'If the publication exists remove it then create a new one.
			'If the publication doesn't exist create a new one.
			if (jj = 1) then
				publications1.Remove(strComplete)
			end if
			Set publication1 = publications1.Add(strComplete)
			publications1.SetDirect strComplete, reference1
			text.writeline "publish :" &strComplete 
		Next
	Else
			text.writeline "No point with " &strName & " in the name to publish"
	End if

End Sub
