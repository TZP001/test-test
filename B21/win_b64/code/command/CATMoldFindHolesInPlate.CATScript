Language="VBSCRIPT"

Sub CATMain()
'----------------------------------------------------------------------------------------
'  This macro is used to find Holes information 
'  (Diameter, Tolerance, Depth, X, Y, Z, Dx, Dy, Dz, ...) for a given plate of the Mold
'  The Holes coming from Mold Component are resized with the necessary clearance
'  The Holes directly created in the plate with Part Design are displayed 
'  with their existing specifications (Without resizing)

'  The macro prompt first a panel to define the resulting File
'  Then you have to select interactively the Plate in the 3D view

'  Verify first
'	1) that you are in the Mold document (Use Edit Link + Open to open the Mold product if necessary)
'     2) that the Mold Product is the current Product (Highlighted in blue)
'     3) in Tools/Options/General/Parameters & Measure/Knowledge/Language that the TPSPackage is loaded 
'        to enable the search of the Tolerances linked to the Diameter of the Holes (i.e. H7)

'  The output is One txt file that can be read with excel (Use ; as separator)
'  and that can be inserted (Use Insert + Object command) in the CATDrawing document related to the Plate

'  Origin of the Plate:
'	X, Y = Middle of the plate
'	Z    = Top of the Plate 
'----------------------------------------------------------------------------------------
Dim sTitle As String
sTitle = "Define the output File"
Dim sTextFile1 As String
Dim sDirectory As String
sDirectory = "Output File :"
sTextFile1 = InputBox(sDirectory,sTitle,"c:\Temp\HoleParameters.txt")
Dim sFilter (0)
sFilter(0) = "Product"
Dim Selection As Selection
Set Selection = CATIA.ActiveDocument.Selection
sStatus = Selection.SelectElement2(sFilter, "Select a Plate", true)
If (sStatus = "cancel") Then
	Exit Sub
End If
If (Selection.Count = 1) Then
	Dim Product As Product
	set Product = Selection.Item(1).Value
Else
	Msg = "Too many Products selected. You have to select only one Product"
	MsgBox Msg
	Exit Sub
End If

FindHolesInPlate 	Product, sTextFile1

End Sub

'----------------------------------------------------------------------------------------
Sub FindHolesInPlate ( PlateProduct, TextFile )

' --- Creation of the text file
On Error Resume Next
Dim filesys, text, readfile
Set filesys = CreateObject("Scripting.FileSystemObject") 
Set text = filesys.CreateTextFile(TextFile , True)
If (Err <> 0) Then
	Msg = "The File: " &TextFile  & " can not be created in the specified directory"
	MsgBox Msg
	On Error Goto 0
Else
	On Error Goto 0

' --- Find the parameters of the Plate
	Dim shapes1 As Shapes
	Dim NewHybridBody As HybridBody
	Dim PartBody As Body
	Dim Part As Part
	Dim HybridShapeFactory As HybridShapeFactory
	Dim  PlateBox(5) As Double
	On Error Resume Next
	Dim CurSel As Selection
	FindPlateParameters text, PlateProduct, PlateBox, shapes1, Part, PartBody, HybridShapeFactory, NewHybridBody, CurSel
	PlateName = PlateProduct.name
	If (Err <> 0) Then
		Msg = "The Plate: " &PlateName  & " can not be found. Verify that you are in the Mold document (Use Edit Link + Open to open the Mold product if necessary)"
		MsgBox Msg
		On Error Goto 0
	Else
		On Error Goto 0

' --- First line of the output file
		text.WriteLine "HolesIn" & PlateName & "; Diameter (mm); Tolerance; Depth (mm); X (mm); Y (mm); Z (mm); Dx (mm); Dy (mm); Dz (mm); Type; Blind or Through?; Threaded or Not?; ThreadDepth; ThreadDiameter; ThreadPitch; Threadside; HeadDiam; HeadDepth; HeadAngle; BottomType; BottomAngle; AnchorMode; "

' --- Loop on the standard Holes included in the Plate
		ProcessBody PartBody, Part, text, PlateName, PlateBox, CurSel

' --- Loop on the main components included in the Mold
		Dim Mold As AnyObject
		Set Mold = CATIA.ActiveDocument.Product
		ReDim MPTab(11)
		For I = 0 to 11
			MPTab(I) = 0.000000
		Next
		MPTab(0) = 1.000000
		MPTab(4) = 1.000000	
		MPTab(8) = 1.000000	
		ProcessProduct text, Mold, " ", MPTab, PlateProduct, PlateBox, shapes1, Part, PartBody, HybridShapeFactory, NewHybridBody, CurSel   
 		CurSel.Clear()
 		CurSel.Add(NewHybridBody)
 		CurSel.Delete()
		text.close

	End If
End If

End Sub

'----------------------------------------------------------------------------------------
Sub ProcessProduct ( text, Product, MainProductName, MPTab, PlateProduct, PlateBox, shapes1, Part, PartBody, HybridShapeFactory, NewHybridBody, CurSel )

Dim SubProduct As AnyObject
Dim SubProductPosition As Position
ReDim SPTab(11)
ReDim Tab(11)

' --- Number of products in Product
ProductCount = Product.Products.Count
ProductName = Product.name
If ProductCount = 0 Then
' --- It is a Part
	ProcessPart text, Product, MainProductName, MPTab, PlateProduct, PlateBox, shapes1, Part, PartBody, HybridShapeFactory, NewHybridBody, CurSel 
Else
	MainProductName = Product.name

' --- Loop on the sub-product
	For I = 1 to ProductCount
		Set SubProduct = Product.Products.Item(I)
		Set SubProductPosition = SubProduct.Position
		SubProductPosition.GetComponents SPTab
' --- Combination of the positionning matrix
		For II = 0 to 2
			Tab(II)   = MPTab(II)*SPTab(0) + MPTab(II+3)*SPTab(1) + MPTab(II+6)*SPTab(2)
			Tab(II+3) = MPTab(II)*SPTab(3) + MPTab(II+3)*SPTab(4) + MPTab(II+6)*SPTab(5)
			Tab(II+6) = MPTab(II)*SPTab(6) + MPTab(II+3)*SPTab(7) + MPTab(II+6)*SPTab(8)
			Tab(II+9) = MPTab(II+9) + MPTab(II)*SPTab(9) + MPTab(II+3)*SPTab(10) + MPTab(II+6)*SPTab(11)
		Next
		ProcessProduct text, SubProduct, MainProductName, Tab, PlateProduct, PlateBox, shapes1, Part, PartBody, HybridShapeFactory, NewHybridBody, CurSel  
	Next
End If

End Sub

'----------------------------------------------------------------------------------------
Sub ProcessPart ( text, Product, MainProductName, tab, PlateProduct, PlateBox, shapes1, Part, PartBody, HybridShapeFactory, NewHybridBody, CurSel )

Dim Import As Reference
Dim  HolePos(2) As Double
Dim  HoleDir(2) As Double
For K = 0 to 2
	HolePos(K) = 0.000000
	HoleDir(K) = 0.000000
Next	
ProductName = Product.name

'--- Case of DrillHole coming from an assembled component 
RemoveName = "DrillHole" & MainProductName & "(" & ProductName & ")"
FindNumberOfRemoveInPlate  PlateProduct, shapes1, RemoveName, Number, Import
If Number = 1 Then
	FindHolesInComponent text, Product, "DrillHole", tab, HolePos, HoleDir, PlateBox, Part, PartBody, Import, HybridShapeFactory, NewHybridBody, CurSel  
End If

'--- Case of DrillHole coming from an simple component 
RemoveName = "DrillHole" & ProductName
FindNumberOfRemoveInPlate  PlateProduct, shapes1, RemoveName, Number, Import
If Number = 1 Then
	FindHolesInComponent text, Product, "DrillHole", tab, HolePos, HoleDir, PlateBox, Part, PartBody, Import, HybridShapeFactory, NewHybridBody, CurSel  
End If

'--- Case of TapHole coming from an assembled component 
RemoveName = "TapHole" & MainProductName & "(" & ProductName & ")"
FindNumberOfRemoveInPlate  PlateProduct, shapes1, RemoveName, Number, Import
If Number = 1 Then
	FindHolesInComponent text, Product, "TapHole", tab, HolePos, HoleDir, PlateBox, Part, PartBody, Import, HybridShapeFactory, NewHybridBody, CurSel  
End If

'--- Case of TapHole coming from an simple component 
RemoveName = "TapHole" & ProductName
FindNumberOfRemoveInPlate  PlateProduct, shapes1, RemoveName, Number, Import
If Number = 1 Then
	FindHolesInComponent text, Product, "TapHole", tab, HolePos, HoleDir, PlateBox, Part, PartBody, Import, HybridShapeFactory, NewHybridBody, CurSel  
End If

End Sub

'----------------------------------------------------------------------------------------
Sub FindPlateParameters ( text, PlateProduct, PlateBox, shapes1, Part, PartBody, HybridShapeFactory, NewHybridBody, CurSel )

' --- Search of the reference plane and the thickness of the Plate
FindShapesFromInstance PlateProduct, "MechanicalTool.1", shapes1, Part, PartBody 
Dim shapes11 As HybridShapes
FindHybridShapesFromInstance PlateProduct, "Open_body.1", shapes11, HybridShapeFactory, NewHybridBody, CurSel  

Dim RefPartBody As Reference
Set RefPartBody = Part.CreateReferenceFromObject(PartBody)

Dim OriginElements As OriginElements
Set OriginElements = Part.OriginElements
Dim Plane1 As AnyObject
Dim refPlane As Reference
Dim Dir0 As HybridShapeDirection
Dim Dir1 As HybridShapeDirection
Dim Dir2 As HybridShapeDirection
Set Plane1 = OriginElements.PlaneYZ
Set refPlane = Part.CreateReferenceFromObject(Plane1)
Set Dir0 = HybridShapeFactory.AddNewDirection(refPlane)
Set Plane1 = OriginElements.PlaneZX
Set refPlane  = Part.CreateReferenceFromObject(Plane1)
Set Dir1 = HybridShapeFactory.AddNewDirection(refPlane)
Set Plane1 = OriginElements.PlaneXY
Set refPlane = Part.CreateReferenceFromObject(Plane1)
Set Dir2 = HybridShapeFactory.AddNewDirection(refPlane)

FindPlateExtremum text, Part, 0, 0, RefPartBody, Dir0, Dir1, Dir2, PlateBox, HybridShapeFactory, NewHybridBody, CurSel 
FindPlateExtremum text, Part, 1, 0, RefPartBody, Dir1, Dir2, Dir0, PlateBox, HybridShapeFactory, NewHybridBody, CurSel 
FindPlateExtremum text, Part, 2, 0, RefPartBody, Dir2, Dir0, Dir1, PlateBox, HybridShapeFactory, NewHybridBody, CurSel 
FindPlateExtremum text, Part, 0, 1, RefPartBody, Dir0, Dir1, Dir2, PlateBox, HybridShapeFactory, NewHybridBody, CurSel 
FindPlateExtremum text, Part, 1, 1, RefPartBody, Dir1, Dir2, Dir0, PlateBox, HybridShapeFactory, NewHybridBody, CurSel 
FindPlateExtremum text, Part, 2, 1, RefPartBody, Dir2, Dir0, Dir1, PlateBox, HybridShapeFactory, NewHybridBody, CurSel 
CurSel.Clear()

End Sub

'----------------------------------------------------------------------------------------
Sub FindPlateExtremum ( text, Part, J, Imax, RefPartBody, Dir0, Dir1, Dir2, PB, HybridShapeFactory, NewHybridBody, CurSel )

Dim Extremum As HybridShapeExtremum
Set Extremum = HybridShapeFactory.AddNewExtremum(RefPartBody, Dir0, Imax)
NewHybridBody.AppendHybridShape Extremum
CurSel.Add(Extremum)
Extremum.Direction2 = Dir1
Extremum.Direction3 = Dir2
Dim reference As Reference
Set reference = Part.CreateReferenceFromObject(Extremum)
Dim Point1 As HybridShapePointCoord
Set Point1 = HybridShapeFactory.AddNewPointCoordWithReference(0.00,0.00,0.00,reference)
NewHybridBody.AppendHybridShape Point1
CurSel.Add(Point1)
Part.Update
Dim Point As Point
set Point = Point1
Dim  Start(2) As Double
Point.GetCoordinates (Start)
PB(J+3*Imax) = Start(J)

End Sub

'----------------------------------------------------------------------------------------
Sub FindShapesFromInstance ( Product, BodyName, Shapes, Part, PartBody )

Dim RefProductDoc As Document
set RefProductDoc = Product.ReferenceProduct.Parent
Set Part = RefProductDoc.Part
Dim PartBodies As Bodies
Set PartBodies = Part.Bodies
Set PartBody = PartBodies.Item ( BodyName )
Set Shapes = PartBody.Shapes

End Sub

'----------------------------------------------------------------------------------------
Sub FindHybridShapesFromInstance ( Product, BodyName, Shapes, HybridShapeFactory, NewHybridBody, CurSel )

Dim RefProductDoc As Document
set RefProductDoc = Product.ReferenceProduct.Parent
RefProductDoc.Activate
Dim Part As Part
Set Part = RefProductDoc.Part
Dim PartBodies As HybridBodies
Set PartBodies = Part.HybridBodies
Dim Body As HybridBody
Set Body = PartBodies.Item ( BodyName )
Set Shapes = Body.HybridShapes
Set NewHybridBody = PartBodies.Add ()
NewHybridBody.name = "ToBeDeleted"
Set HybridShapeFactory = Part.HybridShapeFactory
Dim Mold As AnyObject
Set Mold = CATIA.ActiveDocument.Product
Set RefProductDoc = Mold.ReferenceProduct.Parent
Set CurSel = RefProductDoc.Selection

End Sub

'----------------------------------------------------------------------------------------
Sub FindNumberOfRemoveInPlate ( PlateProduct, Shapes, RemoveName, Number, Solid )

Dim RefProductDoc As Document
set RefProductDoc = PlateProduct.ReferenceProduct.Parent
Dim Part As Part
Set Part = RefProductDoc.Part
Shapecount =  Shapes.Count
Number = 0
Dim Boole As BooleanShape
Dim Bod As Shapes
Dim Import As Solid
For I = 1 to Shapecount
	Dim Reference As Reference
	Set Reference = Part.CreateReferenceFromObject  ( Shapes.Item(I) ) 
	ShapeName =  Reference.DisplayName   
	If ShapeName = RemoveName Then
		Number = Number + 1
		Set Boole = Shapes.Item(I) 
		Set Bod = Boole.Body.Shapes				
		Set Import = Bod.Item(1)
		Set Solid = Part.CreateReferenceFromObject(Import)
	End If
Next

End Sub

'----------------------------------------------------------------------------------------
Sub FindHolesInComponent ( text, Product, BodyName, tab, HolePos, HoleDir, PlateBox, Part, PartBody, Import, HybridShapeFactory, NewHybridBody, CurSel )

Dim shapes2 As Shape
Dim Reference As Reference
Dim PartBid As Part
ProductName = Product.name	
On Error Resume Next
FindShapesFromInstance Product, BodyName, shapes2, PartBid, Reference 
If (Err <> 0) Then
'	text.WriteLine "Component " & ProductName & " doesn't  contain a " &BodyName
	On Error Goto 0
Else
	On Error Goto 0

	Dim OriginElements As OriginElements
	Set OriginElements = Part.OriginElements
	Dim PlaneYZ As AnyObject
	Set PlaneYZ = OriginElements.PlaneYZ
	Dim refPlaneYZ As Reference
	Set refPlaneYZ  = Part.CreateReferenceFromObject(PlaneYZ)
	Dim PlaneZX As AnyObject
	Set PlaneZX = OriginElements.PlaneZX
	Dim refPlaneZX As Reference
	Set refPlaneZX  = Part.CreateReferenceFromObject(PlaneZX)
	Dim HybridShapeDirectionYZ As HybridShapeDirection
	Set HybridShapeDirectionYZ = HybridShapeFactory.AddNewDirection(refPlaneYZ)
	Dim HybridShapeDirectionZX As HybridShapeDirection
	Set HybridShapeDirectionZX = HybridShapeFactory.AddNewDirection(refPlaneZX)
	Dim RefPartBody As Reference
	Set RefPartBody = Part.CreateReferenceFromObject(PartBody)
	Dim Intersection As HybridShapeIntersection
	Set Intersection = HybridShapeFactory.AddNewIntersection(RefPartBody, Import)
	NewHybridBody.AppendHybridShape Intersection
	CurSel.Add(Intersection)
	On Error Resume Next
	Part.Update
	If (Err <> 0) Then
'		text.WriteLine "No Intersection"
 		CurSel.Clear()
		On Error Goto 0
	Else
		On Error Goto 0
		HoleCount = shapes2.Count
		Dim Hole As Hole
		Dim  HoleStart(2) As Double
		Dim  HoleEnd(2) As Double
		Dim  Start(2) As Double
		Dim  NewHoleDir(2) As Double
		For J = 1 to HoleCount
			For K = 0 to 2
				HolePos(K) = 0.000000
				HoleDir(K) = 0.000000
				NewHoleDir(K) = 0.000000
			Next
			Set Hole =  shapes2.Item(J)
			On Error Resume Next
			GetHoleInParameters text, Hole, HoleDiameter, HoleTolerance, HoleType,HolePos,HoleDir, BlindOrThrough, ThreadedOrNot, ThreadDepth, ThreadDiam,ThreadPitch,ThreadSide, HoleDepth, HeadDiam, HeadDepth, HeadAngle, BottomType, BottomAngle, AnchorMode
			If HoleDepth = 0 AND BlindOrThrough = "Blind" Then
				Dim limit1 As Limit
				Set limit1 = Hole.BottomLimit
				Dim Ref As Reference
				Set Ref = limit1.LimitingElement
				limit1.LimitMode = CAToffsetLimit
				PartBid.Update
				HoleDepth= limit1.Dimension.Value
				Part.Update
			End If
			If (Err <> 0) Then
'				text.WriteLine "This Shape is not a Hole"
				On Error Goto 0
			Else
				On Error Goto 0
				If HoleDepth = 0 Then
'					text.WriteLine "HoleDepth = 0"
				Else
					For II = 0 to 2
						NewHoleDir(II)   = tab(II)*HoleDir(0) + tab(II+3)*HoleDir(1) + tab(II+6)*HoleDir(2)
						HoleStart(II) = tab(II+9) + tab(II)*HolePos(0) + tab(II+3)*HolePos(1) + tab(II+6)*HolePos(2)
					Next	
					For L = 0 to 2
						HoleEnd(L) = HoleStart(L) + HoleDepth*NewHoleDir(L)
					Next	
					DStart = NewHoleDir(0)*HoleStart(0)+NewHoleDir(1)*HoleStart(1)+NewHoleDir(2)*HoleStart(2) 
					DEnd = NewHoleDir(0)*HoleEnd(0)+NewHoleDir(1)*HoleEnd(1)+NewHoleDir(2)*HoleEnd(2) 
					Dim Plane As HybridShapePlaneEquation
					Set Plane = HybridShapeFactory.AddNewPlaneEquation(NewHoleDir(0),NewHoleDir(1),NewHoleDir(2),DStart)
					NewHybridBody.AppendHybridShape Plane
						
					Dim reference3 As Reference
					Set reference3 = Part.CreateReferenceFromObject(Plane)
					CurSel.Add(Plane)

					Dim HybridShapeDirection As HybridShapeDirection
					Set HybridShapeDirection = HybridShapeFactory.AddNewDirection(reference3)
					Dim reference4 As Reference
					Set reference4 = Part.CreateReferenceFromObject(Intersection)

					Dim HybridShapeExtremum1 As HybridShapeExtremum
					Set HybridShapeExtremum1 = HybridShapeFactory.AddNewExtremum(reference4, HybridShapeDirection, 0)
					NewHybridBody.AppendHybridShape HybridShapeExtremum1
					CurSel.Add(HybridShapeExtremum1)
					HybridShapeExtremum1.Direction2 = HybridShapeDirectionYZ
					HybridShapeExtremum1.Direction3 = HybridShapeDirectionZX
					Dim reference5 As Reference
					Set reference5 = Part.CreateReferenceFromObject(HybridShapeExtremum1)
					Dim Point1 As HybridShapePointCoord
					Set Point1 = HybridShapeFactory.AddNewPointCoordWithReference(0.00,0.00,0.00,reference5)
					NewHybridBody.AppendHybridShape Point1
					CurSel.Add(Point1)

					Dim HybridShapeExtremum2 As HybridShapeExtremum
					Set HybridShapeExtremum2 = HybridShapeFactory.AddNewExtremum(reference4, HybridShapeDirection, 1)
					NewHybridBody.AppendHybridShape HybridShapeExtremum2
					CurSel.Add(HybridShapeExtremum2)
					HybridShapeExtremum2.Direction2 = HybridShapeDirectionYZ
					HybridShapeExtremum2.Direction3 = HybridShapeDirectionZX
					Dim reference6 As Reference
					Set reference6 = Part.CreateReferenceFromObject(HybridShapeExtremum2)
					Dim Point2 As HybridShapePointCoord
					Set Point2 = HybridShapeFactory.AddNewPointCoordWithReference(0.00,0.00,0.00,reference6)
					NewHybridBody.AppendHybridShape Point2
					CurSel.Add(Point2)
					Part.Update
					Dim Point As Point
					set Point = Point1
					Point.GetCoordinates (Start)
					Dmin = NewHoleDir(0)*Start(0)+NewHoleDir(1)*Start(1)+NewHoleDir(2)*Start(2)
					set Point = Point2
					Point.GetCoordinates(Start)
					Dmax = NewHoleDir(0)*Start(0)+NewHoleDir(1)*Start(1)+NewHoleDir(2)*Start(2)
					If (Dmax -DStart > 0.001) Then
						For II = 0 to 2
							Start(II)=HoleStart(II)+(Dmin-DStart)*NewHoleDir(II)
						Next
'						Dim Point3 As HybridShapePointCoord
'						Set Point3 = HybridShapeFactory.AddNewPointCoord(Start(0),Start(1),Start(2))
'						NewHybridBody.AppendHybridShape Point3
'						CurSel.Add(Point3)
						If (Abs(Dmax-DStart) - Abs(DEnd-DStart) > 0.001 ) Then Dmax = DEnd 
						HoleDepth=Abs(Dmax-Dmin)
						DeltaStart = Dmin-DStart
						If ThreadDepth>0 Then
							If ThreadDepth>DeltaStart Then
								ThreadDepth = ThreadDepth-DeltaStart
							Else
								ThreadDepth = 0
								ThreadedOrNot = "Not Threaded"
							End If
						End If 
						If HeadDepth>0 Then
							If HeadDepth>DeltaStart Then
								HeadDepth = HeadDepth-DeltaStart
							Else
								HeadDepth = 0
								HoleType = "Simple"
							End If
						End If 
						If (Abs(Dend-Dmax) > 0.001) Then 
							BlindOrThrough = "Through"
						End If
						If (HoleDepth > 0.001) Then 
							FindHoleTolerance text, CurSel, PartBid, BodyName, Hole, HoleTolerance
							PrintHoleAttributes text, J, ProductName, HoleDiameter, HoleTolerance, HoleDepth, Start, PlateBox, NewHoleDir, HoleType, BlindOrThrough,ThreadedOrNot,ThreadDepth, ThreadDiam, ThreadPitch, ThreadSide, HeadDiam, HeadDepth, HeadAngle, BottomType,Bottomangle,AnchorMode
						End If
					End If
				End If
			End If
		Next
		CurSel.Clear()
	End If
End If

End Sub

'**************************************************************************************************************************************
'*
'*ProcessBody subprogram
'*
'*The argument is a body
'*It looks at the shapes of the body and for each : execute a specific code
'*depending on the type of the shape
'*************************************************************************************************************************************
Sub ProcessBody (Body, Part, oText1, ProductName, PlateBox, CurSel)

	Dim HoleStart(2) As Double
	Dim HoleDir(2) As Double
	Dim Hole As Hole

	Dim Reference As Reference
	Set Reference = Part.CreateReferenceFromObject(Body) 
	BodyName =  Reference.DisplayName

	Dim Shaps As Shapes
	Set Shaps = Body.Shapes				
	Dim L As Long
	J=0
	For L=1 To Shaps.Count
		Dim Shap As Shape
		Set Shap = Shaps.Item(L)

			Select Case TypeName(Shap)
		
			Case "Hole"
				J=J+1
				Set Hole = Shaps.Item(L)
     				GetHoleInParameters oText1, Hole, HoleDiameter, HoleTolerance, HoleType,HoleStart,HoleDir, BlindOrThrough, ThreadedOrNot, ThreadDepth, ThreadDiam,ThreadPitch,ThreadSide, HoleDepth, HeadDiam, HeadDepth, HeadAngle, BottomType, BottomAngle, AnchorMode
				FindHoleTolerance text, CurSel, Part, BodyName, Hole, HoleTolerance
				PrintHoleAttributes oText1, J, ProductName, HoleDiameter, HoleTolerance, HoleDepth,  HoleStart, PlateBox, HoleDir, HoleType, BlindOrThrough,ThreadedOrNot,ThreadDepth, ThreadDiam, ThreadPitch, ThreadSide, HeadDiam, HeadDepth, HeadAngle, BottomType,Bottomangle,AnchorMode
		
			Case "Pad"
					
			Case "ShapeInstance"
				
			Case "Remove"
				Dim Boole As BooleanShape
				Set Boole = Shap
				Dim Bod As Body
				Set Bod = Boole.Body				
				ProcessBody Bod, Part, oText1, ProductName, PlateBox, CurSel

			Case "Add"
				Dim Boole0 As BooleanShape
				Set Boole0 = Shap
				Dim Bod0 As Body
				Set Bod0 = Boole0.Body				
				ProcessBody Bod, Part, oText1, ProductName, PlateBox, CurSel
			
			Case "Assemble"
				Dim Boole1 As BooleanShape
				Set Boole1 = Shap
				Dim Bod1 As Body
				Set Bod1 = Boole1.Body				
				ProcessBody Bod1, Part, oText1, ProductName, PlateBox, CurSel

			Case "Solid"
			'	Dim Import As Solid
			'	Set Import = Shap
			'	Dim Base1 As CATBaseDispatch
			'	Base1 = Empty
			'	Set Base1 = Import.SourceElement	
			'	If Not Err Then
			'		If Not IsEmpty(Base1) Then
			'									
			'			Redim Preserve SolidShapesStack(NbSolidShapes)
			'			Set SolidShapesStack(NbSolidShapes) = Shap
			'			NbSolidShapes = NbSolidShapes + 1
			'
			'			Dim Bod2 As Body
			'			Set Bod2 = Base1	
			'			ProcessBody Bod2, Part, oText1, ProductName, PlateBox, CurSel
			'			
			'			NbSolidShapes = NbSolidShapes - 1
			'			
			'		End If
			'	End If
			'	Dim ImportedSolid As Solid
			'	Set ImportedSolid = Shap
			'	Dim Element
			'	Set Element = importedSolid.SourceElement
			'	Msgbox Element.Name				

			End Select
		Next	



End Sub		

' ******************************************************************************************
' Purpose:	retrieve the characteristics of Hole feature
'
' Inputs:	oHole:			the hole feature
'
' ******************************************************************************************
Sub GetHoleInParameters(text, oHole, HoleDiameter, HoleTolerance, HoleType, dCoordArray, dDirArray, BlindOrThrough,ThreadedOrNot,ThreadDepth, ThreadDiam, ThreadPitch, ThreadSide, HoleDepth, HeadDiam, HeadDepth, HeadAngle, BottomType,Bottomangle,AnchorMode)

oHole.GetOrigin dCoordArray
oHole.GetDirection dDirArray

    ' Hole Diameter
    HoleDiameter=oHole.Diameter.Value

    ' Hole Type
    If oHole.Type = CATSimpleHole Then
        HoleType = "Simple"
    ElseIf oHole.Type = CATTaperedHole Then
        HoleType = "Tapered"
    ElseIf oHole.Type = CATCounterboredHole Then
        HoleType = "Counterbored"
    ElseIf oHole.Type = CATCountersunkHole Then
        HoleType = "Countersunk"
    Else
        HoleType = "Counterdrilled"
    End If

    'Blind or through?
     If oHole.bottomlimit.limitMode=CAToffsetLimit Then
	BlindOrThrough = "Blind"
	HoleDepth= oHole.BottomLimit.Dimension.Value
    ElseIf oHole.bottomlimit.limitMode=catUpToPlaneLimit Then
	BlindOrThrough = "Blind"
	HoleDepth=0
    Else
	BlindOrThrough = "Through"
	HoleDepth=0
   End If

    'Threaded or Not?
    If  oHole.ThreadingMode=CATThreadedHolethreading Then
	ThreadedOrNot= "Threaded"
	Set holeThreadDepth=oHole.ThreadDepth
	Set holeThreadDiam=oHole.ThreadDiameter
	Set holeThreadPitch=oHole.ThreadPitch
	ThreadDepth=holeThreadDepth.value
	ThreadDiam=holeThreadDiam.value
	ThreadPitch= holeThreadPitch.value
	If oHole.ThreadSide = CATRightThreadSide Then
		ThreadSide= "Right-Threaded"
	Else
		ThreadSide= "Left-Threaded"
      End If
    Else 
	ThreadedOrNot = "Not Threaded"
	ThreadDiam=0
	ThreadDepth=0
	ThreadPitch=0
                 Threadside= "/"
    End If
        
   'HeadDiam & HeadDepth
    If oHole.Type =  CATCounterboredHole OR oHole.Type=CATCounterdrilledHole Then
	Set HoleHeadDiam=oHole.HeadDiameter
	Set HoleHeadDepth=oHole.HeadDepth
	HeadDiam=HoleHeadDiam.Value
	HeadDepth=HoleHeadDepth.Value
   Else
	HeadDiam=0
	HeadDepth=0
   End If

  'HeadAngle
  If oHole.Type= CATCounterdrilledHole OR oHole.Type= CATCountersunkHole OR oHole.Type=CATTaperedHole Then
	Set HoleHeadAngle=oHole.HeadAngle
	HeadAngle=HoleHeadAngle.value
  Else
	HeadAngle=0
  End If

   'BottomType
     If oHole.BottomType = CATFLatHoleBottom Then
        BottomType = "Flat"
        BottomAngle = 0
    Else
        BottomType = "V"
        Set HoleBottomAngle=oHole.BottomAngle
        BottomAngle= HoleBottomAngle.value
     End If

    'AnchorMode
    If oHole.Type=CATCounterdrilledHole OR oHole.Type=CATCounterboredHole Then
   	 If oHole.AnchorMode=CATExtremPointHoleAnchor Then
		AnchorMode="Top of its head"
	Else
		AnchorMode="Bottom of its head"
	End If
   Else
	AnchorMode = "/" 
   End If

End Sub

'----------------------------------------------------------------------------------------
Sub FindHoleTolerance( text, CurSel, Part, BodyName, oHole, HoleTolerance )

    '--- Hole Tolerance
Dim Reference As Reference
Set Reference = Part.CreateReferenceFromObject(oHole) 
ShapeName =  Reference.DisplayName

strTol = "Tol" &ShapeName
Dim parameters1 As Parameters
Set parameters1 = Part.Parameters
Dim strParam1 As StrParam
Set strParam1 = parameters1.CreateString(strTol, "")
CurSel.Add(strParam1)

Dim relations1 As Relations
Set relations1 = Part.Relations
strTolFormula = "TolFormula" &ShapeName
strFormula = BodyName &"\" &ShapeName &"\" &"Diameter.SemanticDimTabValue"   
Dim formula1 As Formula
Set formula1 = relations1.CreateFormula(strTolFormula, "", strParam1, strFormula)
CurSel.Add(formula1)
HoleTolerance = strParam1.Value

End Sub

'----------------------------------------------------------------------------------------
Sub PrintHoleAttributes ( text, J, ProductName, HoleDiameter, HoleTolerance, HoleDepth, HoleStart, PB, HoleDir, HoleType, BlindOrThrough,ThreadedOrNot,ThreadDepth, ThreadDiam, ThreadPitch, ThreadSide, HeadDiam, HeadDepth, HeadAngle, BottomType,Bottomangle,AnchorMode)
'--- The X origin is the Middle of the Plate
HoleStart(0)=HoleStart(0)-(PB(0)+PB(3))/2
'--- The Y origin is the Middle of the Plate
HoleStart(1)=HoleStart(1)-(PB(1)+PB(4))/2
'--- The Z origin is the Top of the Plate
HoleStart(2)=HoleStart(2)-PB(5)
HoleMainPrint= "Hole" &J &"From" &ProductName &"; " &FormatNumber(HoleDiameter,3) &"; " &HoleTolerance &"; " &FormatNumber(HoleDepth,3) &"; " &FormatNumber(HoleStart(0),3) &"; " &FormatNumber(HoleStart(1),3) &"; "  &FormatNumber(HoleStart(2),3) &"; " &FormatNumber(HoleDir(0 ),3) &"; " &FormatNumber(HoleDir(1),3) &"; " &FormatNumber(HoleDir(2),3) &"; " 
HoleMainPrint= HoleMainPrint &HoleType &"; " &BlindOrThrough &"; " &ThreadedOrNot &"; " &FormatNumber(ThreadDepth,3)  &"; " &FormatNumber(ThreadDiam,3) &"; " &ThreadPitch &"; " &ThreadSide &"; " &FormatNumber(HeadDiam,3) &"; " &FormatNumber(HeadDepth,3) &"; " &FormatNumber(HeadAngle,3) &"; " &BottomType & "; " &BottomAngle &"; " &AnchorMode &"; "
text.writeline HoleMainPrint

End Sub
