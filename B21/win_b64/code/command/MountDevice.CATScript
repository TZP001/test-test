'// ---------- CATIAV5 application objects
'====================================================================================
Sub CATMain () 'Method to mount Devices on to a Robot 
'====================================================================================
'*************************************************************************************
'* Select IRB_1400 as the Robot                                                                                                						 *
'* Devices: A V5 Device                                                              																		 *
'*          4 Rocker2 (With Base Tag and Tool Tag(BT), With Base Tag Alone(B),       										 *
'*                      With tool Tag Alone(T),Without tool tag and Base Tag(N))     												 *     
'*************************************************************************************
Dim processDoc as PPRDocument
set processDoc = CATIA.ActiveDocument.PPRDocument

Dim rsrcs as Products
set rsrcs = processDoc.Resources

Dim objRobot as Product
Dim objProduct as Product
Dim objDevice as Product

Dim count
Dim name as String
count=rsrcs.Count

for i=1 to count
Set objProduct  = rsrcs.item(i)
name= objProduct.Name
if(name="IRB_1400.1") then
   Set objRobot=objProduct
end If
next 

Dim objMountManager as MountManager
Set objMountManager = objRobot.GetTechnologicalObject("MountManager" )

Dim ModifyRef As Boolean

ModifyRef = TRUE

Dim TCPMatrix(5) as List
TCPMatrix(0)=0
TCPMatrix(1)=0
TCPMatrix(2)=0
TCPMatrix(3)=0
TCPMatrix(4)=0
TCPMatrix(5)=0
name1 = "NEW_BT"
name2 = "NEW_T"
name3 = "NEW_B"
name4 = "NEW_N"

Dim obj(0) As  String
obj(0) ="CATIAProduct"
Dim object as Product
Dim object1 as Product
Dim BaseTag as Tag
Dim ToolTag as Tag

msgbox("Mounting Rocker2 with Base Tag and Tool Tag on Robot..Select it Now")

CATIA.ActiveDocument.Selection.SelectElement2 obj ,"Select the Device ",True
Set object= CATIA.ActiveDocument.Selection.FindObject("CATIAProduct")

CATIA.ActiveDocument.Selection. Clear ( )
msgbox("Select the Base Tag now")
CATIA.ActiveDocument.Selection.SelectElement2 obj ,"Select the BaseTag ",True
Set object1= CATIA.ActiveDocument.Selection.FindObject("CATIAProduct")
Set BaseTag=object1.GetTechnologicalObject("Tag" )

CATIA.ActiveDocument.Selection. Clear ( )
msgbox("Select the Tool Tag now")
CATIA.ActiveDocument.Selection.SelectElement2 obj ,"Select the ToolTag ",True
Set object1= CATIA.ActiveDocument.Selection.FindObject("CATIAProduct")
Set ToolTag=object1.GetTechnologicalObject("Tag" )

objMountManager.MountDevice object,name1,TCPMatrix,ModifyRef,ToolTag,BaseTag

msgbox("Mounting Rocker2 with Tool Tag on Robot..Select it Now")

CATIA.ActiveDocument.Selection.SelectElement2 obj ,"Select the Device ",True
Set object= CATIA.ActiveDocument.Selection.FindObject("CATIAProduct")

CATIA.ActiveDocument.Selection. Clear ( )
msgbox("Select the Tool Tag now")
CATIA.ActiveDocument.Selection.SelectElement2 obj ,"Select the ToolTag ",True
Set object1= CATIA.ActiveDocument.Selection.FindObject("CATIAProduct")
Set ToolTag=object1.GetTechnologicalObject("Tag" )

objMountManager.MountDevice object,name2,TCPMatrix,ModifyRef,ToolTag,Nothing

msgbox("Mounting Rocker2 with Base Tag on Robot..Select it Now")

CATIA.ActiveDocument.Selection.SelectElement2 obj ,"Select the Device ",True
Set object= CATIA.ActiveDocument.Selection.FindObject("CATIAProduct")

CATIA.ActiveDocument.Selection. Clear ( )
msgbox("Select the Base Tag now")
CATIA.ActiveDocument.Selection.SelectElement2 obj ,"Select the BaseTag ",True
Set object1= CATIA.ActiveDocument.Selection.FindObject("CATIAProduct")
Set BaseTag=object1.GetTechnologicalObject("Tag" )


objMountManager.MountDevice object,name3,TCPMatrix,ModifyRef,ToolTag,BaseTag

msgbox("Mounting Rocker2 without any  Base Tag or  Tool Tag on Robot..Select it Now")

CATIA.ActiveDocument.Selection.SelectElement2 obj ,"Select the Device ",True
Set object= CATIA.ActiveDocument.Selection.FindObject("CATIAProduct")

objMountManager.MountDevice object,name4,TCPMatrix,ModifyRef,Nothing,Nothing

End Sub '/////////////////////////////////////////////////////////// CATMain
