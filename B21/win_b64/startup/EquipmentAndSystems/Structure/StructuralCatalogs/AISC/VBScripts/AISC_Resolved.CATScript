'// COPYRIGHT DASSAULT SYSTEMES  1999
'//============================================================================
'//
'// Language="VBSCRIPT"
'// To build catalog
'// 
'// Creation of a resolved sections catalog for Enovia V5
'//
'//============================================================================
'// Major CATIA interface used:
'//
'// interface               VB Name         Remarks
'// -----------            ------------    --------------
'// CATIACatalogDocument   CatalogDocument create catalog
'//
'//============================================================================
Option Explicit
'******************************************************************************
'  GLOBAL variable declarations section
'******************************************************************************
Dim strGInputPath
Dim strGOutputPath
'@@@@@@@@@@@@@@@@@@@@@@@@@@@@@@@@@@@@@@@@@@@@@@@@@@@@@@@@@@@@@@@@@@@@@@@@@@@@@@
'//                       User customizable sections              
'@@@@@@@@@@@@@@@@@@@@@@@@@@@@@@@@@@@@@@@@@@@@@@@@@@@@@@@@@@@@@@@@@@@@@@@@@@@@@@
Const NBGCSVFile = 1
Dim strArrayGCSVFile (1)
'------------------------------------------------------------------------------
Sub InitCSVFileArray ()
'------------------------------------------------------------------------------
strArrayGCSVFile(1) = "AISC_Resolved"
End Sub '/////////////////////////////////////////////// InitCSVFileArray
'------------------------------------------------------------------------------
Sub GetPath ()
'------------------------------------------------------------------------------
  strGInputPath = InputBox("Path of the CSV file input directory:", _
      "Input path for CSV", _
      "e:\users\jcm\adele\SFDFixR11\StructureModelerUI\CNext\startup\components\StructuralCatalogs\AISC\CsvFiles\")
  strGOutputPath = InputBox("Path of the catalog output directory:", _
      "Output path for Catalog", _
      "e:\users\jcm\adele\SFDFixR11\StructureModelerUI\CNext\startup\components\StructuralCatalogs\AISC\")
End Sub '/////////////////////////////////////////////// GetPath
'------------------------------------------------------------------------------
Sub CATMain ()
'------------------------------------------------------------------------------
  Dim objCatalogDoc As Document
  Dim intK As Integer
  Dim strCSVFile
  Dim strCatalogFile
  InitCSVFileArray
  GetPath
  On Error Resume Next
  For intK = 1 to NBGCSVFile
     strCSVFile = strGInputPath & strArrayGCSVFile (intK) & ".csv"
     strCatalogFile = strGOutputPath & strArrayGCSVFile (intK) & ".catalog"
     Set objCatalogDoc = CATIA.Documents.Add("CatalogDocument")
     '---------- Generate catalog
     objCatalogDoc.CreateCatalogFromcsv strCSVFile,strCatalogFile
  Next  'For intK
  MsgBox "Press OK to quit", 0, "CATALOG CREATION COMPLETED"
End Sub '/////////////////////////////////////////////// CATMain
