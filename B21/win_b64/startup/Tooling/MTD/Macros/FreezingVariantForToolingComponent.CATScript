Language="VBSCRIPT"

Sub CATMain()

'---  Input a list of components
'---  This macro is intended to create as many CATParts as there are line in the DT
'--- the DT is removed from the component
'--- the name if the new component is suffixed by the KW parameter REF
'--- the nomenclature property is set with the KW parameter REF
'--- the KW parameters driven by the DT are hidden
'       for the list of components given as input.
'xxxxxxxxxxxxxxx You must allow enough space !xxxxxxxxxxxxxxxxxxxxxxx
'xxxxxxxxxxxxxxx This does not handle the components using KW parameter REFBOM xxxxxxxxxxxxx
'---  Some directories and names must be defined in the first lines of the macro
'**********************************************************************
'------------------------------------------------------------------------------------
' ------------------------------------------------------------------------------
' ------------------------------------------------------------------------------
' ------------------------------------------------------------------------------

' Sample of commands to launch in a command prompt to get the path and name of components in a txt file 
'find E:\MyDir\startup\components\MoldCatalog\Sleeve\Dme\ -name "*.CATPart" |sed -e "s/\//\\/g">ListOfCmp.txt
'
' or else :
' in run : cmd  ( to get a command window )
' in this window : E: ( to be positionned in appropriate drive )
' in this window : cd NoBackup\downloadOfCXR20Rel\intel_a\startup\components\MoldCatalog  ( to be postionned in right directory )
' in this window : dir /s /B  *.CATPart > MyListOfComponents.txt
'------------------------------------------------------------------------------------
' ------------------------------------------------------------------------------
' ------------------------------------------------------------------------------
' ------------------------------------------------------------------------------
'**********************************************************************

'**********************************************************************
'------------------------------------------------------------------------------------
' ------------------------------------------------------------------------------
' ------------------------------------------------------------------------------
' ------------------------------------------------------------------------------
' Please, the following path of files can be modified to meet your requirements.


' this is the path of directory where the list of components will be found 
    FromDir = "E:\MyFolder\Output\"
' this is the path of the directory where the output files will be created
    WhereDir =  "E:\MyFolder\Output\"

' this is the name of the list of components ( a txt file containing all the component path, one per line, no suffix )
    ListOfComponents = "MyResolvedComponentsList"
' this is the name of the report file
    ReportFileName = "MyReportFile"        '   ( no suffix )



'------------------------------------------------------------------------------------
' ------------------------------------------------------------------------------
' ------------------------------------------------------------------------------
' ------------------------------------------------------------------------------
'**********************************************************************
err.clear

	Dim COLORBGHTML As String, COLORTXTHTML As String
	Dim LANCEMENT_EN_BATCH As String
	LANCEMENT_EN_BATCH  = CATIA.SystemService.Environ("RUN_BATCH")

	COLORBGHTML=WHITE
	COLORTXTHTML=BLACK

'**********************************************************************
	ListOfCmpFile = FromDir&ListOfComponents&".txt"	' for the input file
	ReportFile = WhereDir&ReportFileName&".txt"   '  for report file


' ListOfCmp.txt = file that contains the path of all components (CATPart) to test
' -------------------------------------------------------------------------------
Dim filesys, MyCmp
Set filesys = CreateObject("Scripting.FileSystemObject") 
on error resume next
Set MyCmp = filesys.OpenTextFile(ListOfCmpFile)
If (Err <> 0) Then
	Msg = "The file: " &ListOfCmpFile  & " of components to test does not exist"
	MsgBox Msg
	On Error Goto 0
Else

' ReportIndexFile.txt = File that contains all the files read
' -------------------------------------------------------------------------------------------------------------------
	Dim filesysIF, textIF
	Set filesysIF = CreateObject("Scripting.FileSystemObject") 

' ReportNoFile.txt = File that contains the results of the files not found
' -------------------------------------------------------------------------------------------------------------------
	Dim filesysNF, textNF
	Set filesysNF = CreateObject("Scripting.FileSystemObject") 

' ReportFileName.txt = file that contains the report
' -------------------------------------------------------------------------------------------------------------------
	Dim filesysRP, textRP
	Set filesysRP = CreateObject("Scripting.FileSystemObject") 

'------------------------------------------------------------------------------------------------------------------------
'------------------------------------------------------------------------------------------------------------------------
'------------------------------------------------------------------------------------------------------------------------
'------------------------------------------------------------------------------------------------------------------------
'------------------------------------------------------------------------------------------------------------------------
'------------------------------------------------------------------------------------------------------------------------
'------------------------------------------------------------------------------------------------------------------------------------------------
	Dim encore, wego
	encore = true
	wego = true
    tstrp = false

' Ask to analyze ?
' ------------------------------
    Msgbox "Make sure the Tools/option -no automatic back up- is -ON-"
	Message = "Would you like to freeze the current components variants ? This is irreversible"
	Style = vbYesNo + vbDefaultButton2    'Define buttons.
	Title = "Freezing Tooling Components Variants"
	Response = MsgBox(Message, Style, Title)
	If Response = vbYes Then
        tstRP= true
	End If

	if ( tstrp  ) then  Set textRP = filesys.CreateTextFile(ReportFile , True)


'--------------end of dialog -------------------------------------------

	If (not tstrp) then
		MsgBox "Sorry there are no other option available !!!"
		wego = false
	else

' The tests start !!!
        NBcmp=0
		do while (encore)

'            Checking if this is the last component
			CmpRead = MyCmp.AtEndOfStream
			if (CmpRead) then
'				MsgBox "End"
				encore = false
			else
'				MsgBox "Go on"
'               Reading the next component
				CmpRead = MyCmp.ReadLine
                Nbcmp=Nbcmp+1
'               Opening it
				Set documents1 = CATIA.Documents
				tstNF = true
                on error resume next
				Set partDocument1 = documents1.Open(CmpRead)
				If (Err <> 0) Then
                    msgbox "The file: " &CmpRead  & " does not exist"
					tstNF = false
                    err.clear
                else

'               The component is good
'				MsgBox "Current line = " &CmpRead
				if (tstRP) then
					textRP.WriteLine Nbcmp &" Component: " & CmpRead
					ProcessComponents  textRP, CmpRead
	                PartDocument1.Save
	                PartDocument1.Close
				end if

				end if
			end if
		loop
	end if


	if (tstRP) then textRP.Close

	if (wego) then MsgBox "Do not forget to set your Components as Read Only !!!"
End If

End Sub

'----------------------------------------------------------------------------------------
' Sub to freeze variants
'----------------------------------------------------------------------------------------

   Sub ProcessComponents ( text, CmpFile )


   NbPbEncountered = 0

'---- Deleting of the Design Table

'-- identification of the DesignTable
   err.clear
   On Error resume next
    Set partDocument1 = CATIA.ActiveDocument
	Set selection1 = partDocument1.Selection
	Dim part1 As Part
	Set part1 = partDocument1.Part
	Partname=Part1.name


    selection1.Clear 

' Search the design table via the parameter named Ref
	Dim relations1 As Relations
	Set relations1 = part1.Relations
	Dim parameters1 As Parameters
	Set parameters1 = part1.Parameters
	Dim RefParam As Parameter
	Set RefParam = parameters1.Item("Ref")
	RefName = RefParam.Name
	'text.writeline "param name =  " &RefName
	Dim relation0 As Relation
	set relation0 = RefParam.OptionalRelation
	text.writeline "Name of design table =  " &relation0.Name
	Set designTable1 = relations1.Item(relation0.name)
    selection1.Add designTable1
    selection1.Delete 

'--- creation of nomenclature value and modification of Part number
' nb de caracters du Partname
       nbcharF=1
       For I =1 to 1000
       if ( Right (Partname,nbcharF)<>Partname ) then
            nbcharF=nbcharF+1
       else
             I=2000           
       end if
       next
     ShortName="Not Set"
     for NBchar=1 to NbCharF
          TryName= Left (PartName,NBChar)
          ILast= Right (TryName,1)
          if ( Ilast="_" ) then
                      ShortName= Left (PartName,NBChar-1)
                      NBChar=NbCharF+1
          end if
      next
      if (ShortName="Not Set") then
            ShortName= PartName
      end if
      LongName=ShortName&"_"&RefParam.value


    Set product1 = partDocument1.GetItem(Partname)
    Set product1 = product1.ReferenceProduct
    product1.PartNumber = LongName
    product1.Nomenclature = RefParam.Value

'----------------------
'hiding the parameters to make them not editable

        Set RootParam = parameters1.RootParameterSet
        Set RootParamDirect =RootParam.DirectParameters
        nbparam=RootParamDirect.count

	For I = 1 to NbParam
		Set intParamI = RootParamDirect.Item(I)
		intParamI.Hidden = True
	Next
'-----------------------------------------------







if (NbPbEncountered > 0) then
	text.WriteLine "<B><FONT COLOR=RED> ---> Number of problems found " & NbPbEncountered  & "</B></FONT>"
else
	text.WriteLine "---> No problem found"
end if
text.WriteLine " "

End Sub
