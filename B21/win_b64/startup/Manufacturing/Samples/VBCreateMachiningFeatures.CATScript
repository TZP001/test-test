Option Explicit
' Language="VBSCRIPT"
' ****************************************************************************
' Purpose:       To generate machinable features in the Manufacturing View
'				 This script will create Manufacturing Machinable Area and
'				 Manufacturing Machinable Geometry feature nodes in the 
'				 Manufacturing View.
'
' Assumptions:   A NC Manufacturing document should be open with at least
'				 one Part Operation in the Process List and one associated 
'				 Product in the Product Lit
'
' Script Version: 9
'
' Languages:     VBScript
' V5 Version:    V5R8 SP1
' Reg. Settings: English (United States)
' ****************************************************************************
'*******************************************************************************
'*
'* Global variables
'*
'*******************************************************************************

' these are the general manufacturing variables retrieve by InitMfg()
Dim MfgDoc As Document '           the current document
Dim MfgNbOfPO As Long '            the number of Part Operation

Dim MfgFeatures As ManufacturingFeatures 'Manufacturing Features
Dim PPRProds As PPRProducts  '      Products of the products list
Dim CurrentProduct As Product
Dim SolidShapesStack() As Variant
Dim NbSolidShapes As Long

'*******************************************************************************************
'*
'* Main Entry  Point
'*  
'* It calls the InitMfg Subprogram which initialyze the general variables of the macro.
'* It scans the products of the PPR tree, and for each product : calls the ProcessProdcutInstance Subprogram
'*******************************************************************************************
Sub CATMain()

	' initialize all the manufacturing variables
	InitMfg
	If IsEmpty(MfgDoc) Then
		MsgBox "No current document !", vbCritical + vbOKOnly
		Exit Sub
	End If
	If MfgNbOfPO = 0 Then
		MsgBox "No Part Operation in the document :  " & MfgDoc.Name & " !", vbCritical + vbOKOnly
		Exit Sub
	End If
	If IsEmpty(MfgFeatures) Then
		MsgBox "Manufacturing Features not retrieved !", vbCritical + vbOKOnly
		Exit Sub
	End If
	If IsEmpty(PPRProds) Then
		MsgBox "PPR products not retrieved !", vbCritical + vbOKOnly
		Exit Sub
	End If
	If Err Then
		MsgBox "MfgInit Failed" & vbLf & "Error # " & Err.Number & " " & Err.Description
		Exit Sub
	End If

	' End ofinitialization
	'-----------------------------------------------------------------------------

	Dim I As Long
	For I=1 To PPRProds.Count
		Dim Prod As Product
		Set Prod = PPRProds.Item(I)
		ProcessProductInstance Prod
	Next	


	' OK, bye-bye
	MsgBox "Macro ended OK !", vbInformation + vbOKOnly

End Sub	
' End of main program

'**********************************************************************************
'*
'* ProcessProductInstance subprogram
'*  
'* The argument is a product instance
'* It looks at the product reference of this instance and then looks at this reference is a part or not.
'*     If this is a part : calls the ProcessPart SubProgram
'*     If this is not a part : this is a product which has itself some product instances.
'*			                   so it calls the ProcessProduct SubProgram again for each of these instances
'**********************************************************************************
Sub ProcessProductInstance (ByRef TheProduct As Product)
	
	Dim Ref As Product
	Set Ref = TheProduct.ReferenceProduct
	Dim HasAPart As boolean
	
	HasAPart = Ref.HasAMasterShapeRepresentation 
	
	If (HasAPart) Then

		Dim ShapeRep As CATBaseDispatch
		Set ShapeRep = Ref.GetMasterShapeRepresentation (FALSE)
		
		Dim PartDoc As PartDocument
		Set PartDoc = ShapeRep
		Dim Prt As Part	
		Prt = Empty
		Set Prt = PartDoc.Part
		If IsEmpty(Prt) Then
			MsgBox "Part not retrieved !", vbCritical + vbOKOnly
			Exit Sub
		End If

		Set CurrentProduct = TheProduct
		ProcessPart Prt		
	Else	
		Dim Prods As Products
		Set Prods = TheProduct.Products
		
		Dim J As Long
		For J=1 To Prods.Count
			Dim Prod As Product
			Set Prod = Prods.Item(J)
			ProcessProductInstance Prod
		Next	
	End If

End Sub		



'**********************************************************************************
'*
'* ProcessPart subprogram
'*  
'* The argument is a part
'* It looks at the bodies of the part and for each : calls the ProcessBody SubProgram
'**********************************************************************************

Sub ProcessPart (ByRef ThePart As Part)
	
	Dim Bod As Body
	Set Bod = ThePart.MainBody
	ProcessBody Bod

End Sub		

'**********************************************************************************
'*
'* ProcessBody subprogram
'*  
'* The argument is a body
'* It looks at the shapes of the body and for each : execute a specific code
'* depending on the type of the shape.
'**********************************************************************************

Sub ProcessBody (ByRef TheBody As Body)

	Dim Shaps as Shapes
	Set Shaps = TheBody.Shapes

	Dim L As Long
	For L=1 To Shaps.Count
		Dim Shap As Shape
		Set Shap = Shaps.Item(L)
		
			Select Case TypeName(Shap)
		
			Case "Hole"
				CreateMAF Shap, "hole"
		
			Case "Pad"
				CreateMAF Shap, "pad"
	
			Case "ShapeInstance"
				CreateMAF Shap, "UDF"

			Case "Remove"
				Dim Boole As BooleanShape
				Set Boole = Shap
				Dim Bod As Body
				Set Bod = Boole.Body				
				ProcessBody Bod

			Case "Add"
				Dim Boole0 As BooleanShape
				Set Boole0 = Shap
				Dim Bod0 As Body
				Set Bod0 = Boole0.Body				
				ProcessBody Bod
			
			Case "Assemble"
				Dim Boole1 As BooleanShape
				Set Boole1 = Shap
				Dim Bod1 As Body
				Set Bod1 = Boole1.Body				
				ProcessBody Bod1

			Case "Solid"
				Dim Import As Solid
				Set Import = Shap
				Dim Base1 As CATBaseDispatch
				Base1 = Empty
				Set Base1 = Import.SourceElement	
				If Not Err Then
					If Not IsEmpty(Base1) Then
												
						Redim Preserve SolidShapesStack(NbSolidShapes)
						Set SolidShapesStack(NbSolidShapes) = Shap
						NbSolidShapes = NbSolidShapes + 1

						Dim Bod2 As Body
						Set Bod2 = 	Base1	
						ProcessBody Bod2
						
						NbSolidShapes = NbSolidShapes - 1
						
					End If
				End If

			End Select
	Next	

End Sub		
'**********************************************************************************
		
Sub CreateMAF (ByRef TheShape As Shape, ByRef TheType As CATBSTR)
	
	' Do not create the feature if it already exists
	Dim Iexist As Long
	Iexist = 0
	IsMAFExist TheShape, TheType, Iexist

	If (Iexist = 1) Then
		Exit Sub
	End If

	'--- create a new machining area feature in the manufacturing view
	Dim MyMfgFeature As ManufacturingFeature
	MyMfgFeature = Empty
	Set MyMfgFeature = MfgFeatures.Add("MfgMachinableAreaFeature")
	If IsEmpty(MyMfgFeature) Then
		MsgBox "Manufacturing Machinable Area Feature not created !", vbCritical + vbOKOnly
		Exit Sub
	End If

	Dim MyMfgMachinableArea As ManufacturingMachinableArea
	Set MyMfgMachinableArea = MyMfgFeature
	If IsEmpty(MyMfgMachinableArea) Then
		MsgBox "The preceding Manufacturing Feature was not a Manufacturing Machinable Area Feature !", vbCritical + vbOKOnly
		Exit Sub
	End If

	MyMfgMachinableArea.Name = "MachinableFeature"
	MyMfgMachinableArea.FeatType = TheType
	
	'--- create a new machining geom feature in the manufacturing view
	MyMfgFeature = Empty
	Set MyMfgFeature = MfgFeatures.Add("MfgMachinableGeomFeature")
	If IsEmpty(MyMfgFeature) Then
		MsgBox "Manufacturing Machinable Area Feature not created !", vbCritical + vbOKOnly
		Exit Sub
	End If

	Dim MyMfgMachinableGeom As ManufacturingMachinableGeom
	Set MyMfgMachinableGeom = MyMfgFeature
	If IsEmpty(MyMfgMachinableGeom) Then
		MsgBox "The preceding Manufacturing Feature was not a Manufacturing Machinable Geom Feature !", vbCritical + vbOKOnly
		Exit Sub
	End If
	
	MyMfgMachinableGeom.Shared = 0
	MyMfgMachinableGeom.FeatType = "DesignFeature"
	if (NbSolidShapes > 0) Then
		MyMfgMachinableGeom.AddPointedGeometry TheShape, CurrentProduct, SolidShapesStack
	Else
    Dim EmptyListOfShape() As Variant
    Redim EmptyListOfShape(0)
		MyMfgMachinableGeom.AddPointedGeometry TheShape, CurrentProduct, EmptyListOfShape
	End If

	MyMfgMachinableArea.AddMachinableGeometry MyMfgMachinableGeom

End Sub

'*****************************************************************************
'*
'* InitMfg
'*
'*****************************************************************************
Sub InitMfg()

	MfgDoc = Empty
	MfgNbOfPO = 0
	PPRProds = Empty
    MfgFeatures = Empty
	Redim SolidShapesStack(0)
	NbSolidShapes = 0

	' Get current Document
	On Error Resume Next
	Set MfgDoc = CATIA.ActiveDocument
	If Err Then
		Exit Sub
	End If

	' Retrieve current Process Root
	Dim ActivityRef As AnyObject
	Set ActivityRef = MfgDoc.GetItem("Process")

	' Retrieve first Part Operation
	Dim Mfg1stPO As ManufacturingSetup
	Mfg1stPO = Empty
	
	If (ActivityRef.IsSubTypeOf("PhysicalActivity")) Then

		Dim childs As Activities
		Set childs = ActivityRef.ChildrenActivities
		if childs.Count <= 0 then
			Exit Sub
		End if

		Dim I As Long
		For I=1 To childs.Count
			Dim child As Activity
			Set child = childs.Item(I)
			If (child.IsSubTypeOf("ManufacturingSetup")) Then
				Set Mfg1stPO = child
				MfgNbOfPO = MfgNbOfPO + 1
				Exit For
			End If
		Next

	End If
	If MfgNbOfPO <= 0 Then
		Exit Sub
	End If

	' get the manufacturing view
	Dim MfgView As ManufacturingView
	Set MfgView = Mfg1stPO.GetManufacturingView
	If IsEmpty(MfgView) Then
		MsgBox "Manufacturing View not retrieved !", vbCritical + vbOKOnly
		Exit Sub
	End If

	' get the list of manufacturing features
	Set MfgFeatures = MfgView.ManufacturingFeatures

	Dim PPRDoc As PPRDocument
	PPRDoc = Empty	
	Set PPRDoc = MfgDoc.PPRDocument
	If Err Then
		Exit Sub
	End If
	If IsEmpty(PPRDoc) Then
		Exit Sub
	End If

	Set PPRProds = PPRDoc.Products

End Sub

'**********************************************************************************
'*
'* IsMAFExist subprogram
'*  
'* Arguments are TheShape (Design feature) and the type of the new MAF
'**********************************************************************************
		
Sub IsMAFExist (ByRef TheShape As Shape, ByRef TheType As CATBSTR, ByRef Exist As Long)
	
	Exist = 0
	Dim CurMfgFeat As ManufacturingFeature
	Dim CurMfgMachArea As ManufacturingMachinableArea
	Dim CurMfgMachGeom As ManufacturingMachinableGeom
	Dim MachinableGeometryListSize As Long
	Dim MachinableGeometryList() As Variant
	Dim PointedGeometryListSize As Long
    Dim PointedShapes() As Variant

	Dim I As Long
	For I=1 To MfgFeatures.Count
		Set CurMfgFeat = MfgFeatures.Item(I)
		If (TypeName(CurMfgFeat) = "ManufacturingMachinableArea") Then
				
			Set CurMfgMachArea = CurMfgFeat
			
			If (CurMfgFeat.FeatType = TheType) Then
			
				MachinableGeometryListSize = CurMfgMachArea.MachinableGeometryCount
				If (MachinableGeometryListSize = 1)	Then	
	
					ReDim MachinableGeometryList(MachinableGeometryListSize) 
					CurMfgMachArea.ListMachinableGeometry MachinableGeometryList
					Set CurMfgMachGeom = MachinableGeometryList(0)
					PointedGeometryListSize = CurMfgMachGeom.PointedGeometryCount
					If (PointedGeometryListSize = 1) Then		

						Dim PointedGeometry As Variant
						Dim PointedProduct As Product
						Dim NbPointedShapes As Long

						CurMfgMachGeom.ListPointedGeometry 1, PointedGeometry, PointedProduct, NbPointedShapes
						If (NbPointedShapes > 0) Then
							Redim PointedShapes(NbPointedShapes-1)
							CurMfgMachGeom.ListShapesOfPointedGeometry 1, PointedShapes
						End If
						
						If (PointedGeometry.Name = TheShape.Name) Then
							If (PointedProduct.Name = CurrentProduct.Name) Then		
								If (NbSolidShapes = NbPointedShapes) Then
									Exist = 1 ' Possible to be correct, check the name of each imported body
									Dim J As Long
									For J = 0 To NbPointedShapes-1
										If Not (SolidShapesStack(J).Name = PointedShapes(J).Name) Then
  											Exist = 0
											Exit For
										End If
									Next
									If (Exist = 1) Then
										Exit For
									End If
								End If
							End If
						End If
					End If
				End If
			End If
		End If
	Next

End Sub
