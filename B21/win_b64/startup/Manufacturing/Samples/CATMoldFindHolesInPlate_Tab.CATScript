Language="VBSCRIPT"

Sub CATMain()

' The  two macros can be copied everywhere but be ensure that the root of create_holes_patterns.CATScript
' is correctly write in CATMoldFindHolesInPlate_Tab.CATScript in LibraryName

'----------------------------------------------------------------------------------------
'  This macro is used to find Holes information 
'  (Diameter, Tolerance, Depth, X, Y, Z, Dx, Dy, Dz, ...) for a given plate of the Mold
'  The Holes coming from Mold Component are resized with the necessary clearance
'  The Holes directly created in the plate with Part Design are displayed 
'  with their existing specifications (Without resizing)

'  The macro prompt first a panel to define the resulting File
'  Then you have to select interactively the Plate in the 3D view

'  Verify first
'	1) that you are in the Mold document (Use Edit Link + Open to open the Mold product if necessary)    
'     2) in Tools/Options/General/Parameters & Measure/Knowledge/Language that the TPSPackage is loaded 
'        to enable the search of the Tolerances linked to the Diameter of the Holes (i.e. H7)

'  The output is One txt file that can be read with excel (Use ; as separator)
'  and that can be inserted (Use Insert + Object command) in the CATDrawing document related to the Plate

'  Origin of the Plate:
'	X, Y = Middle of the plate
'	Z    = Top of the Plate 
'----------------------------------------------------------------------------------------
Dim sTitle As String
sTitle = "Define the output File"
Dim sTextFile1 As String
Dim sDirectory As String
sDirectory = "Output File :"
'sTextFile1 = InputBox(sDirectory,sTitle,"c:\Temp\HoleParameters.txt")
Dim sFilter (0)
sFilter(0) = "Product"
Dim Selection As Selection
Set Selection = CATIA.ActiveDocument.Selection
sStatus = Selection.SelectElement2(sFilter, "Select a Plate", true)
If (sStatus = "cancel") Then
	Exit Sub
End If
If (Selection.Count = 1) Then
	Dim Product As Product
	set Product = Selection.Item(1).Value
Else
	Msg = "Too many Products selected. You have to select only one Product"
	MsgBox Msg
	Exit Sub
End If

On Error Resume Next
'Dim filesys, text, readfile
'Set filesys = CreateObject("Scripting.FileSystemObject") 
'Set text = filesys.CreateTextFile(sTextFile1 , True)
'If (Err <> 0) Then
'	Msg = "The File: " &sTextFile1  & " can not be created in the specified directory"
'	MsgBox Msg
'	Exit Sub
'End If

Dim HName(5000) As CATSafeArrayVariant
Dim HDiam(5000) As Double
Dim HTole(5000) As CATSafeArrayVariant
Dim HDept(5000) As Double
Dim HLocX(5000) As Double
Dim HLocY(5000) As Double
Dim HLocZ(5000) As Double
Dim HAxeX(5000) As Double
Dim HAxeY(5000) As Double
Dim HAxeZ(5000) As Double
Dim HType(5000) As CATSafeArrayVariant	' Tye of hole
Dim HBlin(5000) As CATSafeArrayVariant	' Blind or Through
Dim HThrd(5000) As CATSafeArrayVariant	' Threaded or not
Dim HThDe(5000) As Double			' Thread depth
Dim HThDi(5000) As Double			' Thread diameter
Dim HThPi(5000) As Double			' Thread pitch
Dim HThSi(5000) As CATSafeArrayVariant	' Thread side
Dim HHDia(5000) As Double			' Head diameter
Dim HHDep(5000) As Double			' Head depth
Dim HHAng(5000) As Double			' Head angle
Dim HBTyp(5000) As CATSafeArrayVariant	' Bottom type
Dim HBAng(5000) As Double			' Bottom angle
Dim HAnch(5000) As CATSafeArrayVariant	' Anchor mode
NbHoles = -1

FindHolesInPlate 	Product, text, NbHoles,HName,HDiam,HTole,HDept,HLocX,HLocY,HLocZ,HAxeX,HAxeY,HAxeZ,HType,HBlin,HThrd,HThDe,HThDi,HThPi,HThSi,HHDia,HHDep,HHAng,HBTyp,HBAng,HAnch

'text.WriteLine "NbHoles = " &FormatNumber(NbHoles,1)
If (NbHoles > 0) Then
'	For I = 0 to NbHoles
'		HoleCheck = "Hole " &I &" Name " &HName(I) &" Diameter " &FormatNumber(HDiam(I),3)
'		HoleCheck = HoleCheck &" Toler " &HTole(I) &" Depth " &FormatNumber(HDept(I),3)
'		HoleCheck = HoleCheck &" X " &FormatNumber(HLocX(I),3) &" Y " &FormatNumber(HLocY(I),3) &" Z " &FormatNumber(HLocZ(I),3)
'		HoleCheck = HoleCheck &" DX " &FormatNumber(HAxeX(I),3) &" DY " &FormatNumber(HAxeY(I),3) &" DZ " &FormatNumber(HAxeZ(I),3)
'		HoleCheck = HoleCheck &" Type " &HType(I)
'		text.WriteLine HoleCheck
'		HoleCheck = " Blind " & HBlin(I) &" Thread " &HThrd(I)
'		HoleCheck = HoleCheck &" ThDep " &FormatNumber(HThDe(I),3) &" ThDia " &FormatNumber(HThDi(I),3) &" Pitch " &FormatNumber(HThPi(I),3)
'		HoleCheck = HoleCheck &" ThSide " &HThSi(I)
'		HoleCheck = HoleCheck &" HeadDia " &FormatNumber(HHDia(I),3) &" HeadDep " &FormatNumber(HHDep(I),3) &" HeadAng " &FormatNumber(HHAng(I),3)
'		HoleCheck = HoleCheck &" BtType " & HBTyp(I) &" BtAng " &FormatNumber(HBAng(I),3)
'		HoleCheck = HoleCheck &" Anchor " & HAnch(I)
'		text.WriteLine HoleCheck
'	Next

	Dim mySystemService
	Dim iLibraryName As String
	Dim iType As CatScriptLibraryType
	Dim iProgramName As String
	Dim iFunctionName As String
	Dim iParameters(24) As CATSafeArrayVariant

	Set mySystemService = CATIA.SystemService

	iLibraryName = "E:\MACROS\"

	' Added by cvr to manage ODT
	Dim AdlOdtTmp As String
	Dim Slash As String
	Dim AdlOdtTmpPath As String
	AdlOdtTmp = mySystemService.Environ("ADL_ODT_TMP")
	mySystemService.Print "AdlOdtTmp=" & AdlOdtTmp
	Slash = mySystemService.Environ("ADL_ODT_SLASH")
	mySystemService.Print "Slash=" & Slash
	AdlOdtTmpPath = AdlOdtTmp & Slash
	mySystemService.Print "Path=" & AdlOdtTmpPath
	If AdlOdtTmpPath <> "" Then
		iLibraryName = AdlOdtTmpPath
	End If

	iType = catScriptLibraryTypeDirectory
	iProgramName = "create_holes_pattern.CATScript"
	iFunctionName = "CATMain"

	iParameters(0)  = NbHoles
	iParameters(1)  = HName
	iParameters(2)  = HDiam
	iParameters(3)  = HTole
	iParameters(4)  = HDept
	iParameters(5)  = HLocX
	iParameters(6)  = HLocY
	iParameters(7)  = HLocZ
	iParameters(8)  = HAxeX
	iParameters(9)  = HAxeY
	iParameters(10) = HAxeZ
	iParameters(11) = HType
	iParameters(12) = HBlin
	iParameters(13) = HThrd
	iParameters(14) = HThDe
	iParameters(15) = HThDi
	iParameters(16) = HThPi
	iParameters(17) = HThSi
	iParameters(18) = HHDia
	iParameters(19) = HHDep
	iParameters(20) = HHAng
	iParameters(21) = HBTyp
	iParameters(22) = HBAng
	iParameters(23) = HAnch
	Set RefProd = Product.ReferenceProduct
	Set ParentPrat =  RefProd.Parent
	FileToOpen = ParentPrat.FullName
	iParameters(24) = FileToOpen 

    
	mySystemService.ExecuteScript iLibraryName, iType, iProgramName, iFunctionName, iParameters
End If

'text.close

End Sub

'----------------------------------------------------------------------------------------
Sub FindHolesInPlate ( PlateProduct, text, NbHoles,HName,HDiam,HTole,HDept,HLocX,HLocY,HLocZ,HAxeX,HAxeY,HaxeZ,HType,HBlin,HThrd,HThDe,HThDi,HThPi,HThSi,HHDia,HHDep,HHAng,HBTyp,HBAng,HAnch)

' --- Creation of the text file
On Error Resume Next
	On Error Goto 0

' --- Find the parameters of the Plate
	Dim shapes1 As Shapes
	Dim NewHybridBody As HybridBody
	Dim PartBody As Body
	Dim Part As Part
	Dim PartOrig As Part
	Dim Parent1 As AnyObject
	Dim Parent2 As AnyObject
	Dim HybridShapeFactory As HybridShapeFactory
	Dim  PlateBox(5) As Double
	On Error Resume Next
	Dim CurSel As Selection
	FindPlateParameters text, PlateProduct, PlateBox, shapes1, Part, PartBody, HybridShapeFactory, NewHybridBody, CurSel
	PlateName = PlateProduct.name
	If (Err <> 0) Then
		Msg = "The Plate: " &PlateName  & " can not be found. Verify that you are in the Mold document (Use Edit Link + Open to open the Mold product if necessary)"
		MsgBox Msg
		On Error Goto 0
	Else
		On Error Goto 0

		Set Parent1 = PlateProduct.Parent
		Parent1Name = Parent1.name	
'		text.WriteLine "Parent1(PlateProduct) = " & Parent1Name
		Set Parent2 = Parent1.Parent
		Parent2Name = Parent2.name	
'		text.WriteLine "Parent2(PlateProduct) = " & Parent2Name
' --- First line of the output file
'		text.WriteLine "HolesIn" & PlateName & "; Diameter (mm); Tolerance; Depth (mm); X (mm); Y (mm); Z (mm); Dx (mm); Dy (mm); Dz (mm); Type; Blind or Through?; Threaded or Not?; ThreadDepth; ThreadDiameter; ThreadPitch; Threadside; HeadDiam; HeadDepth; HeadAngle; BottomType; BottomAngle; AnchorMode; "

		Dim Intersection As HybridShapeIntersection
		ReDim MBTab(11)
		For I = 0 to 11
			MBTab(I) = 0.000000
		Next
		MBTab(0) = 1.000000
		MBTab(4) = 1.000000	
		MBTab(8) = 1.000000	
' --- Loop on the main components included in the Mold
		Dim Mold As AnyObject
		Set Mold = CATIA.ActiveDocument.Product
		ReDim MPTab(11)
		For I = 0 to 11
			MPTab(I) = 0.000000
		Next
		MPTab(0) = 1.000000
		MPTab(4) = 1.000000	
		MPTab(8) = 1.000000	
		ReDim MSTab(11)
		Set ProductPosition0 = PlateProduct.Position
		ProductPosition0.GetComponents MSTab

		Dim  PBmin(2) As Double
		Dim  PBmax(2) As Double
		ReDim InvTab(11)
		Dim  NewPlateBox(5) As Double

		For I = 0 to 5
			NewPlateBox(I) = PlateBox(I)
		Next
		PBmin(0) = PlateBox(0)
		PBmin(1) = PlateBox(1)
		PBmin(2) = PlateBox(2)
		PBmax(0) = PlateBox(3)
		PBmax(1) = PlateBox(4)
		PBmax(2) = PlateBox(5)
		Deter = MSTab(0)*(MSTab(4)*MSTab(8) - MSTab(5)*MSTab(7))
		Deter = Deter - MSTab(3)*(MSTab(1)*MSTab(8) - MSTab(2)*MSTab(7))
		Deter = Deter + MSTab(6)*(MSTab(1)*MSTab(5) - MSTab(4)*MSTab(2))
		If (Deter <> 0) Then
			InvTab(0) = (MSTab(4)*MSTab(8) - MSTab(7)*MSTab(5)) / Deter
			InvTab(1) = (MSTab(2)*MSTab(7) - MSTab(8)*MSTab(1)) / Deter
			InvTab(2) = (MSTab(1)*MSTab(5) - MSTab(4)*MSTab(2)) / Deter
			InvTab(3) = (MSTab(5)*MSTab(6) - MSTab(8)*MSTab(3)) / Deter
			InvTab(4) = (MSTab(0)*MSTab(8) - MSTab(6)*MSTab(2)) / Deter
			InvTab(5) = (MSTab(2)*MSTab(3) - MSTab(5)*MSTab(0)) / Deter
			InvTab(6) = (MSTab(3)*MSTab(7) - MSTab(6)*MSTab(4)) / Deter
			InvTab(7) = (MSTab(1)*MSTab(6) - MSTab(7)*MSTab(0)) / Deter
			InvTab(8) = (MSTab(0)*MSTab(4) - MSTab(1)*MSTab(3)) / Deter
			For II = 0 to 2
				NewPlateBox(II)   = MSTab(II+9) + InvTab(II)*PBmin(0) + InvTab(II+3)*PBmin(1) + InvTab(II+6)*PBmin(2)
				NewPlateBox(II+3) = MSTab(II+9) + InvTab(II)*PBmax(0) + InvTab(II+3)*PBmax(1) + InvTab(II+6)*PBmax(2)
			Next	
		End If

' --- Loop on the standard Holes included in the Plate
		Icase = 0
		ProcessBody2 NbHoles,HName,HDiam,HTole,HDept,HLocX,HLocY,HLocZ,HAxeX,HAxeY,HAxeZ,HType,HBlin,HThrd,HThDe,HThDi,HThPi,HThSi,HHDia,HHDep,HHAng,HBTyp,HBAng,HAnch, Icase, PartBody, Part, text, PlateName, NewPlateBox, CurSel, HybridShapeFactory, NewHybridBody, shapes1, MBTab, MSTab, Intersection, Part, Parent2

 		CurSel.Add(NewHybridBody)
 		CurSel.Cut()
		Part.InWorkObject = PartBody

	End If

End Sub

'----------------------------------------------------------------------------------------
Sub FindPlateParameters ( text, PlateProduct, PlateBox, shapes1, Part, PartBody, HybridShapeFactory, NewHybridBody, CurSel )

' --- Search of the reference plane and the thickness of the Plate
FindShapesFromInstance PlateProduct, "MechanicalTool.1", shapes1, Part, PartBody 
Dim shapes11 As HybridShapes
FindHybridShapesFromInstance PlateProduct, "Open_body.1", shapes11, HybridShapeFactory, NewHybridBody, CurSel  

Dim RefPartBody As Reference
Set RefPartBody = Part.CreateReferenceFromObject(PartBody)

Dim OriginElements As OriginElements
Set OriginElements = Part.OriginElements
Dim Plane1 As AnyObject
Dim refPlane As Reference
Dim Dir0 As HybridShapeDirection
Dim Dir1 As HybridShapeDirection
Dim Dir2 As HybridShapeDirection
Set Plane1 = OriginElements.PlaneYZ
Set refPlane = Part.CreateReferenceFromObject(Plane1)
Set Dir0 = HybridShapeFactory.AddNewDirection(refPlane)
Set Plane1 = OriginElements.PlaneZX
Set refPlane  = Part.CreateReferenceFromObject(Plane1)
Set Dir1 = HybridShapeFactory.AddNewDirection(refPlane)
Set Plane1 = OriginElements.PlaneXY
Set refPlane = Part.CreateReferenceFromObject(Plane1)
Set Dir2 = HybridShapeFactory.AddNewDirection(refPlane)

FindPlateExtremum text, Part, 0, 0, RefPartBody, Dir0, Dir1, Dir2, PlateBox, HybridShapeFactory, NewHybridBody, CurSel 
FindPlateExtremum text, Part, 1, 0, RefPartBody, Dir1, Dir2, Dir0, PlateBox, HybridShapeFactory, NewHybridBody, CurSel 
FindPlateExtremum text, Part, 2, 0, RefPartBody, Dir2, Dir0, Dir1, PlateBox, HybridShapeFactory, NewHybridBody, CurSel 
FindPlateExtremum text, Part, 0, 1, RefPartBody, Dir0, Dir1, Dir2, PlateBox, HybridShapeFactory, NewHybridBody, CurSel 
FindPlateExtremum text, Part, 1, 1, RefPartBody, Dir1, Dir2, Dir0, PlateBox, HybridShapeFactory, NewHybridBody, CurSel 
FindPlateExtremum text, Part, 2, 1, RefPartBody, Dir2, Dir0, Dir1, PlateBox, HybridShapeFactory, NewHybridBody, CurSel 
CurSel.Cut()

End Sub

'----------------------------------------------------------------------------------------
Sub FindPlateExtremum ( text, Part, J, Imax, RefPartBody, Dir0, Dir1, Dir2, PB, HybridShapeFactory, NewHybridBody, CurSel )

Dim Extremum As HybridShapeExtremum
Set Extremum = HybridShapeFactory.AddNewExtremum(RefPartBody, Dir0, Imax)
NewHybridBody.AppendHybridShape Extremum
CurSel.Add(Extremum)
Extremum.Direction2 = Dir1
Extremum.Direction3 = Dir2
Dim reference As Reference
Set reference = Part.CreateReferenceFromObject(Extremum)
Dim Point1 As HybridShapePointCoord
Set Point1 = HybridShapeFactory.AddNewPointCoordWithReference(0.00,0.00,0.00,reference)
NewHybridBody.AppendHybridShape Point1
CurSel.Add(Point1)
Part.Update
Dim Point As Point
set Point = Point1
Dim  Start(2) As Double
Point.GetCoordinates (Start)
PB(J+3*Imax) = Start(J)

End Sub

'----------------------------------------------------------------------------------------
Sub FindShapesFromInstance ( Product, BodyName, Shapes, Part, PartBody )

Dim RefProductDoc As Document
set RefProductDoc = Product.ReferenceProduct.Parent
Set Part = RefProductDoc.Part
Dim PartBodies As Bodies
Set PartBodies = Part.Bodies
Set PartBody = PartBodies.Item ( BodyName )
Set Shapes = PartBody.Shapes

End Sub

'----------------------------------------------------------------------------------------
Sub FindHybridShapesFromInstance ( Product, BodyName, Shapes, HybridShapeFactory, NewHybridBody, CurSel )

Dim RefProductDoc As Document
set RefProductDoc = Product.ReferenceProduct.Parent
RefProductDoc.Activate
Dim Part As Part
Set Part = RefProductDoc.Part
Dim PartBodies As HybridBodies
Set PartBodies = Part.HybridBodies
Dim Body As HybridBody
Set Body = PartBodies.Item ( BodyName )
Set Shapes = Body.HybridShapes
Set NewHybridBody = PartBodies.Add ()
NewHybridBody.name = "ToBeDeleted"
Set HybridShapeFactory = Part.HybridShapeFactory
Dim Mold As AnyObject
Set Mold = CATIA.ActiveDocument.Product
Set RefProductDoc = Mold.ReferenceProduct.Parent
Set CurSel = RefProductDoc.Selection

End Sub

'**************************************************************************************************************************************
'*
'*ProcessBody2 subprogram
'*
'*The argument is a body
'*It looks at the shapes of the body and for each : execute a specific code
'*depending on the type of the shape
' Inputs:	Icase:	0 = a	pure feature hole
'				#0 a hole coming from a remove or else
'*************************************************************************************************************************************
Sub ProcessBody2 (NbHoles,HName,HDiam,HTole,HDept,HLocX,HLocY,HLocZ,HAxeX,HAxeY,HAxeZ,HType,HBlin,HThrd,HThDe,HThDi,HThPi,HThSi,HHDia,HHDep,HHAng,HBTyp,HBAng,HAnch, Icase, Body, Part, oText1, ProductName, PlateBox, CurSel, HybridShapeFactory, NewHybridBody, shapes1, MBTab, MSTab, Intersection, PartOrig, PlateParent)

Dim HolePos(2) As Double
Dim HoleStart(2) As Double
Dim HoleEnd(2) As Double
Dim Start(2) As Double
Dim NewStart(2) As Double
Dim HoleDir(2) As Double
Dim NewHoleDir(2) As Double
Dim Hole As Hole

Dim OriginElements As OriginElements
Set OriginElements = PartOrig.OriginElements
Dim PlaneYZ As AnyObject
Set PlaneYZ = OriginElements.PlaneYZ
Dim refPlaneYZ As Reference
Set refPlaneYZ  = PartOrig.CreateReferenceFromObject(PlaneYZ)
Dim PlaneZX As AnyObject
Set PlaneZX = OriginElements.PlaneZX
Dim refPlaneZX As Reference
Set refPlaneZX  = PartOrig.CreateReferenceFromObject(PlaneZX)
Dim HybridShapeDirectionYZ As HybridShapeDirection
Set HybridShapeDirectionYZ = HybridShapeFactory.AddNewDirection(refPlaneYZ)
Dim HybridShapeDirectionZX As HybridShapeDirection
Set HybridShapeDirectionZX = HybridShapeFactory.AddNewDirection(refPlaneZX)

Dim Reference As Reference
Set Reference = Part.CreateReferenceFromObject(Body) 
BodyName =  Reference.DisplayName
'oText1.WriteLine "BodyName = " & BodyName

On Error Resume Next


Dim Shaps As Shapes
Set Shaps = Body.Shapes				
Dim L As Long
J=0
For L=1 To Shaps.Count
	Dim Shap As Shape
	Set Shap = Shaps.Item(L)

	Select Case TypeName(Shap)

	'==========
	Case "Hole"
	'==========
		J=J+1
		Set Hole = Shaps.Item(L)
     		GetHoleInParameters oText1, Hole, HoleDiameter, HoleTolerance, HoleType,HolePos,HoleDir, BlindOrThrough, ThreadedOrNot, ThreadDepth, ThreadDiam,ThreadPitch,ThreadSide, HoleDepth, HeadDiam, HeadDepth, HeadAngle, BottomType, BottomAngle, AnchorMode
		
		If Icase = 0 Then
			FindHoleTolerance text, CurSel, Part, BodyName, Hole, HoleTolerance
			PrintHoleAttributes NbHoles,HName,HDiam,HTole,HDept,HLocX,HLocY,HLocZ,HAxeX,HAxeY,HAxeZ,HType,HBlin,HThrd,HThDe,HThDi,HThPi,HThSi,HHDia,HHDep,HHAng,HBTyp,HBAng,HAnch, oText1, J, ProductName, HoleDiameter, HoleTolerance, HoleDepth,  HolePos, PlateBox, HoleDir, HoleType, BlindOrThrough,ThreadedOrNot,ThreadDepth, ThreadDiam, ThreadPitch, ThreadSide, HeadDiam, HeadDepth, HeadAngle, BottomType,Bottomangle,AnchorMode
		Else
			For II = 0 to 2
				NewHoleDir(II)	= MBTab(II)*HoleDir(0) + MBTab(II+3)*HoleDir(1) + MBTab(II+6)*HoleDir(2)
				HoleStart(II)	= MBTab(II+9) + MBTab(II)*HolePos(0) + MBTab(II+3)*HolePos(1) + MBTab(II+6)*HolePos(2)
			Next	
			For II = 0 to 2
				HoleEnd(II) = HoleStart(II) + HoleDepth*NewHoleDir(II)
			Next	
			DStart = NewHoleDir(0)*HoleStart(0)+NewHoleDir(1)*HoleStart(1)+NewHoleDir(2)*HoleStart(2) 
			DEnd = NewHoleDir(0)*HoleEnd(0)+NewHoleDir(1)*HoleEnd(1)+NewHoleDir(2)*HoleEnd(2) 
			Dim Plane As HybridShapePlaneEquation
			Set Plane = HybridShapeFactory.AddNewPlaneEquation(NewHoleDir(0),NewHoleDir(1),NewHoleDir(2),DStart)
			NewHybridBody.AppendHybridShape Plane
						
			Dim reference3 As Reference
			Set reference3 = PartOrig.CreateReferenceFromObject(Plane)
			CurSel.Add(Plane)

			Dim HybridShapeDirection As HybridShapeDirection
			Set HybridShapeDirection = HybridShapeFactory.AddNewDirection(reference3)
			Dim reference4 As Reference
			Set reference4 = PartOrig.CreateReferenceFromObject(Intersection)

			Dim HybridShapeExtremum1 As HybridShapeExtremum
			Set HybridShapeExtremum1 = HybridShapeFactory.AddNewExtremum(reference4, HybridShapeDirection, 0)
			NewHybridBody.AppendHybridShape HybridShapeExtremum1
			CurSel.Add(HybridShapeExtremum1)
			HybridShapeExtremum1.Direction2 = HybridShapeDirectionYZ
			HybridShapeExtremum1.Direction3 = HybridShapeDirectionZX
			Dim reference5 As Reference
			Set reference5 = PartOrig.CreateReferenceFromObject(HybridShapeExtremum1)

			Dim Point1 As HybridShapePointCoord
			Set Point1 = HybridShapeFactory.AddNewPointCoordWithReference(0.00,0.00,0.00,reference5)
			NewHybridBody.AppendHybridShape Point1
			CurSel.Add(Point1)

			Dim HybridShapeExtremum2 As HybridShapeExtremum
			Set HybridShapeExtremum2 = HybridShapeFactory.AddNewExtremum(reference4, HybridShapeDirection, 1)
			NewHybridBody.AppendHybridShape HybridShapeExtremum2
			CurSel.Add(HybridShapeExtremum2)
			HybridShapeExtremum2.Direction2 = HybridShapeDirectionYZ
			HybridShapeExtremum2.Direction3 = HybridShapeDirectionZX
			Dim reference6 As Reference
			Set reference6 = PartOrig.CreateReferenceFromObject(HybridShapeExtremum2)
			Dim Point2 As HybridShapePointCoord
			Set Point2 = HybridShapeFactory.AddNewPointCoordWithReference(0.00,0.00,0.00,reference6)
			NewHybridBody.AppendHybridShape Point2
			CurSel.Add(Point2)
			PartOrig.Update
			If (Err <> 0) Then
'				oText1.WriteLine "No Extremum"
				CurSel.Cut()
				On Error Goto 0
			End If
			Dim Point As Point
			set Point = Point1
			Point.GetCoordinates (Start)
			For II = 0 to 2
				NewStart(II) = MSTab(II+9) + MSTab(II)*Start(0) + MSTab(II+3)*Start(1) + MSTab(II+6)*Start(2)
			Next	
			Dmin = NewHoleDir(0)*NewStart(0)+NewHoleDir(1)*NewStart(1)+NewHoleDir(2)*NewStart(2)
			set Point = Point2
			Point.GetCoordinates(Start)
			For II = 0 to 2
				NewStart(II) = MSTab(II+9) + MSTab(II)*Start(0) + MSTab(II+3)*Start(1) + MSTab(II+6)*Start(2)
			Next	
			Dmax = NewHoleDir(0)*NewStart(0)+NewHoleDir(1)*NewStart(1)+NewHoleDir(2)*NewStart(2)
				
			If (Dmax -DStart > 0.001) Then
				For II = 0 to 2
					Start(II)=HoleStart(II)+(Dmin-DStart)*NewHoleDir(II)
				Next
				If (Abs(Dmax-DStart) - Abs(DEnd-DStart) > 0.001 ) Then Dmax = DEnd 
				HoleDepth=Abs(Dmax-Dmin)
				DeltaStart = Dmin-DStart
				If ThreadDepth>0 Then
					If ThreadDepth>DeltaStart Then
						ThreadDepth = ThreadDepth-DeltaStart
					Else
						ThreadDepth = 0
						ThreadedOrNot = "Not Threaded"
					End If
				End If 
				If HeadDepth>0 Then
					If HeadDepth>DeltaStart Then
						HeadDepth = HeadDepth-DeltaStart
					Else
						HeadDiam = 0
						HeadDepth = 0
						HeadAngle = 0
						HoleType = "Simple"
						NewHoleDepth = Abs(DEnd-DStart-DeltaStart)
						If (Abs(HoleDepth-NewHoleDepth) < 0.001) Then BlindOrThrough = "Through"
					End If
				End If 
				If (Abs(Dend-Dmax) > 0.001) Then 
					BlindOrThrough = "Through"
				End If
				If (HoleDepth > 0.001) Then 

					FindHoleTolerance text, CurSel, Part, BodyName, Hole, HoleTolerance
'					FindHoleTolerance oText1, CurSel, Part, BodyName, Hole, HoleTolerance
					PrintHoleAttributes NbHoles,HName,HDiam,HTole,HDept,HLocX,HLocY,HLocZ,HAxeX,HAxeY,HAxeZ,HType,HBlin,HThrd,HThDe,HThDi,HThPi,HThSi,HHDia,HHDep,HHAng,HBTyp,HBAng,HAnch, oText1, J, ProductName, HoleDiameter, HoleTolerance, HoleDepth,  Start, PlateBox, NewHoleDir, HoleType, BlindOrThrough,ThreadedOrNot,ThreadDepth, ThreadDiam, ThreadPitch, ThreadSide, HeadDiam, HeadDepth, HeadAngle, BottomType,Bottomangle,AnchorMode
				End If
			End If
		End If

	'=========
	Case "Pad"
	'=========
					
	'===================
	Case "ShapeInstance"
	'===================
				
	'============
	Case "Remove"
	'============
		Dim Boole As BooleanShape
		Set Boole = Shap
		Dim Bod As Body
		Set Bod = Boole.Body
		Dim Bod7 As Shapes
		Dim Import0 As Solid
		Dim Solid0 As Reference

		Set Bod7 = Boole.Body.Shapes				
		Set Import0 = Bod7.Item(1)
		Set Solid0 = Part.CreateReferenceFromObject(Import0)
		Dim RefPartBody As Reference
		Set RefPartBody = Part.CreateReferenceFromObject(Body)
		Set Intersection = HybridShapeFactory.AddNewIntersection(RefPartBody, Solid0)
		NewHybridBody.AppendHybridShape Intersection
		CurSel.Add(Intersection)
		On Error Resume Next
		Part.Update
		If (Err <> 0) Then
'			oText1.WriteLine "No Intersection"
			CurSel.Cut()
			On Error Goto 0
		Else
			Ichoice = 1
			ProcessBody2 NbHoles,HName,HDiam,HTole,HDept,HLocX,HLocY,HLocZ,HAxeX,HAxeY,HAxeZ,HType,HBlin,HThrd,HThDe,HThDi,HThPi,HThSi,HHDia,HHDep,HHAng,HBTyp,HBAng,HAnch, Ichoice, Bod, Part, oText1, ProductName, PlateBox, CurSel, HybridShapeFactory, NewHybridBody, shapes1, MBTab, MSTab, Intersection, PartOrig, PlateParent
		End If

	'=========
	Case "Add"
	'=========
		Dim Boole0 As BooleanShape
		Set Boole0 = Shap
		Dim Bod0 As Body
		Set Bod0 = Boole0.Body				
		Dim Bod9 As Shapes
		Dim Import2 As Solid
		Dim Solid2 As Reference

		Set Bod9 = Boole0.Body.Shapes				
		Set Import2 = Bod9.Item(1)
		Set Solid2 = Part.CreateReferenceFromObject(Import2)
		Dim RefPartBody2 As Reference
		Set RefPartBody2 = Part.CreateReferenceFromObject(Body)
		Set Intersection = HybridShapeFactory.AddNewIntersection(RefPartBody2, Solid2)
		NewHybridBody.AppendHybridShape Intersection
		CurSel.Add(Intersection)
		On Error Resume Next
		Part.Update
		If (Err <> 0) Then
'			oText1.WriteLine "No Intersection"
			CurSel.Cut()
			On Error Goto 0
		Else
			Ichoice = 1
			ProcessBody2 NbHoles,HName,HDiam,HTole,HDept,HLocX,HLocY,HLocZ,HAxeX,HAxeY,HAxeZ,HType,HBlin,HThrd,HThDe,HThDi,HThPi,HThSi,HHDia,HHDep,HHAng,HBTyp,HBAng,HAnch, Ichoice, Bod0, Part, oText1, ProductName, PlateBox, CurSel, HybridShapeFactory, NewHybridBody, shapes1, MBTab, MSTab, Intersection, PartOrig, PlateParent
		End If
			
	'==============
	Case "Assemble"
	'==============
		Dim Boole1 As BooleanShape
		Set Boole1 = Shap
		Dim Bod1 As Body
		Set Bod1 = Boole1.Body
		Dim Bod8 As Shapes
		Dim Import1 As Solid
		Dim Solid1 As Reference

		Set Bod8 = Boole1.Body.Shapes				
		Set Import1 = Bod8.Item(1)
		Set Solid1 = Part.CreateReferenceFromObject(Import1)
		Dim RefPartBody1 As Reference
		Set RefPartBody1 = Part.CreateReferenceFromObject(Body)
		Set Intersection = HybridShapeFactory.AddNewIntersection(RefPartBody1, Solid1)
		NewHybridBody.AppendHybridShape Intersection
		CurSel.Add(Intersection)
		On Error Resume Next
		Part.Update
		If (Err <> 0) Then
'			oText1.WriteLine "No Intersection"
			CurSel.Cut()
			On Error Goto 0
		Else
			Ichoice = 1
			ProcessBody2 NbHoles,HName,HDiam,HTole,HDept,HLocX,HLocY,HLocZ,HAxeX,HAxeY,HAxeZ,HType,HBlin,HThrd,HThDe,HThDi,HThPi,HThSi,HHDia,HHDep,HHAng,HBTyp,HBAng,HAnch, Ichoice, Bod1, Part, oText1, ProductName, PlateBox, CurSel, HybridShapeFactory, NewHybridBody, shapes1, MBTab, MSTab, Intersection, PartOrig, PlateParent
		End If

	'===========
	Case "Solid"
	'===========
		Dim Import As Solid
		Set Import = Shap
		Dim ProductI As AnyObject
		Dim ParentI As AnyObject
		Dim ParentI2 As AnyObject
		Set ProductI = Import.SourceProduct
		Set ParentI = ProductI.Parent
		Set ParentI2 = ParentI.Parent
		ProductIName = ProductI.name	
		ParentIName = ParentI.name	
		ParentIName2 = ParentI2.name	
		PlateParentName = PlateParent.name	
		If ParentIName2 = PlateParentName Then
		End If
		ReDim MATab(11)
		ReDim MCTab(11)
		Set ProductPosition2 = ParentI2.Position
		ProductPosition2.GetComponents MATab

		Set ProductPosition0 = ProductI.Position
		ProductPosition0.GetComponents MCTab
		ReDim MRTab(11)
		For II = 0 to 2
			MRTab(II)   = MATab(II)*MCTab(0) + MATab(II+3)*MCTab(1) + MATab(II+6)*MCTab(2)
			MRTab(II+3) = MATab(II)*MCTab(3) + MATab(II+3)*MCTab(4) + MATab(II+6)*MCTab(5)
			MRTab(II+6) = MATab(II)*MCTab(6) + MATab(II+3)*MCTab(7) + MATab(II+6)*MCTab(8)
			MRTab(II+9) = MATab(II+9) + MATab(II)*MCTab(9) + MATab(II+3)*MCTab(10) + MATab(II+6)*MCTab(11)
		Next

		Dim ProductE As AnyObject
		Set ProductE = Import.SourceElement
		ElementName = ProductE.name	
		Dim Bod2 As Body
		Set Bod2 = ProductE
		Dim Part0 As Part
		Dim RefProductDoc As Document
		set RefProductDoc = ProductI.ReferenceProduct.Parent
		Set Part0 = RefProductDoc.Part

		If ElementName = "DrillHole" OR ElementName = "TapHole" Then
			Ichoice = 1
			ProcessBody2 NbHoles,HName,HDiam,HTole,HDept,HLocX,HLocY,HLocZ,HAxeX,HAxeY,HAxeZ,HType,HBlin,HThrd,HThDe,HThDi,HThPi,HThSi,HHDia,HHDep,HHAng,HBTyp,HBAng,HAnch, Ichoice, Bod2, Part0, oText1, ProductIName, PlateBox, CurSel, HybridShapeFactory, NewHybridBody, shapes1, MRTab, MSTab, Intersection, PartOrig, PlateParent
		End If

	End Select
Next	
' 	CurSel.Cut()

End Sub		


' ******************************************************************************************
' Purpose:	retrieve the characteristics of Hole feature
'
' Inputs:	oHole:	the hole feature
'
' ******************************************************************************************
Sub GetHoleInParameters(text, oHole, HoleDiameter, HoleTolerance, HoleType, dCoordArray, dDirArray, BlindOrThrough,ThreadedOrNot,ThreadDepth, ThreadDiam, ThreadPitch, ThreadSide, HoleDepth, HeadDiam, HeadDepth, HeadAngle, BottomType,Bottomangle,AnchorMode)

oHole.GetOrigin dCoordArray
oHole.GetDirection dDirArray

' Hole Diameter
HoleDiameter=oHole.Diameter.Value

' Hole Type
If oHole.Type = CATSimpleHole Then
	HoleType = "Simple"
ElseIf oHole.Type = CATTaperedHole Then
	HoleType = "Tapered"
ElseIf oHole.Type = CATCounterboredHole Then
	HoleType = "Counterbored"
ElseIf oHole.Type = CATCountersunkHole Then
	HoleType = "Countersunk"
Else
	HoleType = "Counterdrilled"
End If

'Blind or through?
If oHole.bottomlimit.limitMode=CAToffsetLimit Then
	BlindOrThrough = "Blind"
	HoleDepth= oHole.BottomLimit.Dimension.Value
ElseIf oHole.bottomlimit.limitMode=catUpToPlaneLimit Then
	BlindOrThrough = "Blind"
	HoleDepth=0
Else
	BlindOrThrough = "Through"
	HoleDepth=0
End If

'Threaded or Not?
If  oHole.ThreadingMode=CATThreadedHolethreading Then
	ThreadedOrNot= "Threaded"
	Set holeThreadDepth=oHole.ThreadDepth
	Set holeThreadDiam=oHole.ThreadDiameter
	Set holeThreadPitch=oHole.ThreadPitch
	ThreadDepth=holeThreadDepth.value
	ThreadDiam=holeThreadDiam.value
	ThreadPitch= holeThreadPitch.value
	If oHole.ThreadSide = CATRightThreadSide Then
		ThreadSide= "Right-Threaded"
	Else
		ThreadSide= "Left-Threaded"
	End If
Else 
	ThreadedOrNot = "Not Threaded"
	ThreadDiam=0
	ThreadDepth=0
	ThreadPitch=0
	Threadside= "/"
End If
        
'HeadDiam & HeadDepth
If oHole.Type =  CATCounterboredHole OR oHole.Type=CATCounterdrilledHole OR oHole.Type=CATCountersunkHole  Then
	If oHole.Type =  CATCounterboredHole OR oHole.Type=CATCounterdrilledHole Then
		Set HoleHeadDiam=oHole.HeadDiameter
		HeadDiam=HoleHeadDiam.Value
	Else
		HeadDiam=0
	End If
	Set HoleHeadDepth=oHole.HeadDepth
	HeadDepth=HoleHeadDepth.Value
Else
	HeadDiam=0
	HeadDepth=0
End If

'HeadAngle
If oHole.Type= CATCounterdrilledHole OR oHole.Type= CATCountersunkHole OR oHole.Type=CATTaperedHole Then
	Set HoleHeadAngle=oHole.HeadAngle
	HeadAngle=HoleHeadAngle.value
Else
	HeadAngle=0
End If

'BottomType
If oHole.BottomType = CATFLatHoleBottom Then
	BottomType = "Flat"
	BottomAngle = 0
Else
	BottomType = "V"
	Set HoleBottomAngle=oHole.BottomAngle
	BottomAngle= HoleBottomAngle.value
End If

'AnchorMode
If oHole.Type=CATCounterdrilledHole OR oHole.Type=CATCounterboredHole Then
	If oHole.AnchorMode=CATExtremPointHoleAnchor Then
		AnchorMode="Top of its head"
	Else
		AnchorMode="Bottom of its head"
	End If
Else
	AnchorMode = "/" 
End If

End Sub

'----------------------------------------------------------------------------------------
Sub FindHoleTolerance( text, CurSel, Part, BodyName, oHole, HoleTolerance )

    '--- Hole Tolerance
Dim Reference As Reference
Set Reference = Part.CreateReferenceFromObject(oHole) 
ShapeName =  Reference.DisplayName
'text.writeline "ShapeName = " &ShapeName

strTol = "Tol" &ShapeName
Dim parameters1 As Parameters
Set parameters1 = Part.Parameters
Dim strParam1 As StrParam
Set strParam1 = parameters1.CreateString(strTol, "")
CurSel.Add(strParam1)

Dim relations1 As Relations
Set relations1 = Part.Relations
strTolFormula = "TolFormula" &ShapeName
strFormula = BodyName &"\" &ShapeName &"\" &"Diameter.SemanticDimTabValue"   
'text.writeline "strTolFormula= " &strTolFormula
'text.writeline "strFormula= " &strFormula

Dim formula1 As Formula
Set formula1 = relations1.CreateFormula(strTolFormula, "", strParam1, strFormula)
CurSel.Add(formula1)
HoleTolerance = strParam1.Value
'text.writeline "HoleTolerance = " &HoleTolerance

End Sub

'----------------------------------------------------------------------------------------
Sub PrintHoleAttributes (NbHoles,HName,HDiam,HTole,HDept,HLocX,HLocY,HLocZ,HAxeX,HAxeY,HAxeZ,HType,HBlin,HThrd,HThDe,HThDi,HThPi,HThSi,HHDia,HHDep,HHAng,HBTyp,HBAng,HAnch, text, J, ProductName, HoleDiameter, HoleTolerance, HoleDepth, HoleStart, PB, HoleDir, HoleType, BlindOrThrough,ThreadedOrNot,ThreadDepth, ThreadDiam, ThreadPitch, ThreadSide, HeadDiam, HeadDepth, HeadAngle, BottomType,Bottomangle,AnchorMode)
'--- The X origin is the Middle of the Plate
HoleStart(0)=HoleStart(0)-(PB(0)+PB(3))/2
'--- The Y origin is the Middle of the Plate
HoleStart(1)=HoleStart(1)-(PB(1)+PB(4))/2
'--- The Z origin is the Top of the Plate
HoleStart(2)=HoleStart(2)-PB(5)
HoleMainPrint= "Hole" &J &"From" &ProductName &"; " &FormatNumber(HoleDiameter,3) &"; " &HoleTolerance &"; " &FormatNumber(HoleDepth,3) &"; " &FormatNumber(HoleStart(0),3) &"; " &FormatNumber(HoleStart(1),3) &"; "  &FormatNumber(HoleStart(2),3) &"; " &FormatNumber(HoleDir(0 ),3) &"; " &FormatNumber(HoleDir(1),3) &"; " &FormatNumber(HoleDir(2),3) &"; " 
HoleMainPrint= HoleMainPrint &HoleType &"; " &BlindOrThrough &"; " &ThreadedOrNot &"; " &FormatNumber(ThreadDepth,3)  &"; " &FormatNumber(ThreadDiam,3) &"; " &ThreadPitch &"; " &ThreadSide &"; " &FormatNumber(HeadDiam,3) &"; " &FormatNumber(HeadDepth,3) &"; " &FormatNumber(HeadAngle,3) &"; " &BottomType & "; " &BottomAngle &"; " &AnchorMode &"; "
'text.writeline HoleMainPrint

NbHoles = NbHoles + 1
HName(NbHoles) = "Hole" &J &"From" &ProductName 
HDiam(NbHoles) = HoleDiameter
HTole(NbHoles) = HoleTolerance
HDept(NbHoles) = HoleDepth
HLocX(NbHoles) = HoleStart(0)
HLocY(NbHoles) = HoleStart(1)
HLocZ(NbHoles) = HoleStart(2)
HAxeX(NbHoles) = HoleDir(0)
HAxeY(NbHoles) = HoleDir(1)
HAxeZ(NbHoles) = HoleDir(2)
HType(NbHoles) = HoleType
HBlin(NbHoles) = BlindOrThrough 
HThrd(NbHoles) = ThreadedOrNot 
HThDe(NbHoles) = ThreadDepth
HThDi(NbHoles) = ThreadDiam
HThPi(NbHoles) = ThreadPitch 
HThSi(NbHoles) = ThreadSide 
HHDia(NbHoles) = HeadDiam
HHDep(NbHoles) = HeadDepth
HHAng(NbHoles) = HeadAngle
HBTyp(NbHoles) = BottomType 
HBAng(NbHoles) = BottomAngle 
HAnch(NbHoles) = AnchorMode 

End Sub
