''''''''''''''''''''''''''''''''''''''''''''''''''''''''''''''''''''''''''''''''
'
' COPYRIGHT DELMIA CORP. 2004
'
' AnnotationActivity.CATScript
' 
' Description: 
'   The following script is used to obtain all the Annotation Activities 
'   also the names of the annotations associated with it.
'
'''''''''''''''''''''''''''''''''''''''''''''''''''''''''''''''''''''''''''''''''

Language="VBSCRIPT"

Sub CATMain()

    Catia.SystemService.Print "Starting script"

    ' Get the document
    Dim CurrentDoc As Document
    Set CurrentDoc = CATIA.ActiveDocument

    Dim ProcessDoc As PPRDocument
    Set ProcessDoc = CurrentDoc.PPRDocument

	' Get the "Process" Activity
    Dim RootActivity
    Set RootActivity = CurrentDoc.GetItem("Process")

    ' Now get the root activity's children
    Dim RootChildren
    Set RootChildren = RootActivity.ChildrenActivities

    ' Since the first activity is the Start activity we get the second 
    ' activity.	
    Dim aActivity
    count = RootChildren.Count

    if count > 2 then
        For i = 2 to (count-1) 

            Set aActivity = RootChildren.Item(i)

            ' Create a selection and add our activity to it
            Set aSelection = CurrentDoc.Selection
            aSelection.Add (aActivity)	

            Catia.SystemService.Print "Getting a Annotation Activity"

            'Get the Annotation activity.
            Dim AnnotAct as AnnotationActivity
            Set AnnotAct = aSelection.FindObject("DNBIAAnnotationActivity")

            ' Clear the selection
            aSelection.Clear()

            ' Obtain the name of the Annotation Activity
	        Dim ObjectName
	        ObjectName = AnnotAct.Name
	        Catia.SystemService.Print "The Name of the Annotation Activity is = " & ObjectName

	        Dim CompleteStatus
	        CompleteStatus = AnnotAct.CompletionStatus 
	        Catia.SystemService.Print "The Completion Status of the Annotation Activity is = " & CompleteStatus
	        
            Dim AnnotList As DNBIAFTAList

	        ' Get the Annot activities list of objects
            Set  AnnotList  =	AnnotAct.GetFTAList
            num = AnnotList.Count

            If num<> 0  Then
                For j = 1 to num
                    Dim object As Annotation
                     Set object =  AnnotList.Item(j)
   	                Catia.SystemService.Print "The Name of Annotation is = " & object.Name
                next
            End If

        next  ' for i
    End If

    Catia.SystemService.Print "Finished executing script"
          
End Sub
