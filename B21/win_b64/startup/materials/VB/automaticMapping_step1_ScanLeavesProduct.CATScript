' COPYRIGHT DASSAULT SYSTEMES 2004
'
' ***********************************************************************
'   Purpose:		Scan current product to retrieve its leaves products
'
'   Version:		1.0
'   Author:			LGS
'   Languages:		CATScript 
'   Locales:		English 
'   CATIA Level:	V5R14 
' ***********************************************************************
'
'  This interactive VB macro scan the product tree to loook at all the leaves
'  products. The result of the scan is created in an output text file. 
'  Look at the .txt sample delivered to see the text output format.
'  A product should be opened in a CATIA session before starting the macro.
'
Language="VBSCRIPT"

Public oReport As TextStream 
Public arrayOfVisitedNode() As Integer
Public MaxLevel As Integer 
Public sFilOu As String                          ' Output file full path
Const sTmpPath = "E:\tmp"                    
Const sResultFile = "ScanLeavesProducts.txt"     ' Result file name

'*********************************************************************************
'                       Main Program
'*********************************************************************************
Sub CATMain()
    
  On Error Resume Next
    
  '+++++++++++++++++++++++++++++++++++++++++++++++++++++++++++++++++++++++++++++++++
  '                           Initialize environment
  '+++++++++++++++++++++++++++++++++++++++++++++++++++++++++++++++++++++++++++++++++
  ' Deactivate file alert (to avoid interactive message during read/write of files if any)
  Dim FileAlertSave
  FileAlertSave = CATIA.DisplayFileAlerts
  CATIA.DisplayFileAlerts = False
 
  CATinit
  '+++++++++++++++++++++++++++++++++++++++++++++++++++++++++++++++++++++++++++++++++
  ' 					Read the Current Main document
  '+++++++++++++++++++++++++++++++++++++++++++++++++++++++++++++++++++++++++++++++++
  ' 
  ' ----------------------------------- Read product file
  ' 
  Dim oProductDocument As Document
  Set oProductDocument = CATIA.ActiveDocument
  On Error Resume Next
  
  If  (oProductDocument Is Nothing ) Then
    MsgBox "No CATIA document has been loaded ! Please load a CATIA document.", vbExclamation
    Exit Sub
  End If  
  Err.Clear
  '
  ' ----------------------------------- Retrieve the Root Product 
  '
  Dim oRootProduct As Product
  Set oRootProduct = oProductDocument.Product
  '
  ' 
  ' --------------------------------- Retrieve the products contained in the root product 
  ' 
  Redim arrayOfVisitedNode(1)
  ' 
  Dim IndiceLevel As Integer  
  Dim sName As String
  Dim oChildren As Product
  Dim oFather As Product
  Dim oBrotherProduct As Product
  '
  Dim oCurentProduct As Product
  set oCurentProduct = oRootProduct

  IndiceLevel = 0
  MaxLevel = IndiceLevel 

  PrintHeader oProductDocument
  ' 
  ' +++++++++++++++++++++++++++++++++++++++++++++++++++++++++++++++++++++++++++++++++
  '                            Scan Product
  ' +++++++++++++++++++++++++++++++++++++++++++++++++++++++++++++++++++++++++++++++++  
  Do 
       
    If LExistChildren(oCurentProduct) Then
    
      ' Retrieve the first child
      Call GetFirstChild(oCurentProduct, oChildren, IndiceLevel)
      Set oCurentProduct = oChildren 
      IndiceLevel = IndiceLevel + 1  
      If (MaxLevel < IndiceLevel) Then
        Redim Preserve arrayOfVisitedNode(UBound(arrayOfVisitedNode)+1) 
        MaxLevel = MaxLevel + 1
      End If                 

    Else

      Call PrintInfo( oCurentProduct) 
      ' 
      ' oCurentProduct is a leaf. Go up to first non-visited child 
      ' 
      Do while ((Not(oCurentProduct Is oRootProduct)) AND (Not(lExistBrother(oCurentProduct,IndiceLevel))))
        ' 
        ' Get the father
        '         
        IndiceLevel = IndiceLevel - 1
        Call GetFather(oCurentProduct, OFather)
        Set oCurentProduct = OFather
      Loop

      If lExistBrother(oCurentProduct,IndiceLevel) Then
        Call NextBrother(oCurentProduct, oBrotherProduct, IndiceLevel)
        Set oCurentProduct = oBrotherProduct   
      End If        
      
    End If  
         '              
  Loop Until ( oCurentProduct Is oRootProduct )
  '
  ' +++++++++++++++++++++++++++++++++++++++++++++++++++++++++++++++++++++++++++++++++
  '                         End Scan 
  ' +++++++++++++++++++++++++++++++++++++++++++++++++++++++++++++++++++++++++++++++++
  PrintFoot ()
  MsgBox " SCAN ENDED. Consult the result in the file : " & sFilOu 

  ' 
  ' Close the documents
  ' 
  ' oProductDocument.Close
  Set oRootProduct = Nothing
  '  
  Set oProductDocument = Nothing 
  '
  ' Finalize the report file
  '
  oReport.Close
  Set oReport = Nothing
   
  '  
  ' Reactivate file alert
  '
  CATIA.DisplayFileAlerts = FileAlertSave

End Sub
'*********************************************************************************
'  End of Main Program
'********************************************************************************* 


'*********************************************************************************
'  Subroutines
'********************************************************************************* 
'
' ----------------------------------------------------------------------------------
' CATinit
' ----------------------------------------------------------------------------------
Sub CATinit ()

  ' Initialize the report file
  ' 
  ' Delete possibly existing input and output files
  '   
  sFilOu = CATIA.FileSystem.ConcatenatePaths(sTmpPath,sResultFile)

  If (CATIA.FileSystem.FileExists(sFilou)) Then 
    CATIA.FileSystem.DeleteFile sFilOu
  End If
   
  Dim iOverwrite As Boolean
  iOverwrite = True
   
  Set oReport = CATIA.FileSystem.CreateFile(sFilOu,iOverwrite).OpenAsTextStream("ForWriting") 

End Sub

' -----------------------------------------------------------------------------------
' ScanNode
' -----------------------------------------------------------------------------------
Sub ScanNode(oMyProduct As Product, cProductChildren As Products, nb_children As Integer)

  Set cProductChildren = oMyProduct.Products
  Dim nb_products As Integer
  nb_products = cProductChildren.Count
  nb_children = nb_products

End Sub
' --------------------------------------------------------------------------------------
' LExistChildren
' ---------------------------------------------------------------------------------------

Function LExistChildren( oMyProduct As Product) As Boolean

  Dim cProductChildren As Products
  Dim nb_children As Integer
  Dim Lexist As Boolean
  
  Lexist = False
   
  Call ScanNode(oMyProduct, cProductChildren, nb_children) 
  
  If (nb_children > 0) Then
    Lexist = True
  End If 
  
  LExistChildren = Lexist  

End Function

' -----------------------------------------------------------------------------------------
' GetFirstChild
' -----------------------------------------------------------------------------------------
Sub GetFirstChild(oMyProduct As Product,oMyChild As Product,Currentlevel As Integer)

  Dim cProductChildren As Products
  Dim nbChildren As Integer 

  Dim IndiceFF As Integer 
  IndiceFF = 1
    
  Call ScanNode(oMyProduct, cProductChildren, nbChildren)
  If (NbChildren > 0) Then
    Set oMyChild = cProductChildren.Item(IndiceFF)
  Else
    Set oMyChild = Nothing
  End If

  arrayOfVisitedNode(Currentlevel) = 1
    
End Sub
' -------------------------------------------------------------------------------------
' LexistBrother
' -------------------------------------------------------------------------------------
Function lExistBrother(oMyProduct As Product,Currentlevel As Integer) As Boolean
 
   Dim iPrevious  As Integer
   Dim NBChildren As Integer
   Dim iOther     As Integer
   Dim oFatherProduct As Product
   Dim cChildren As Products
   Dim LOtherBrother As Boolean
   Dim NbFilsAVisiter As Integer
   
   iOther = 0 
   LOtherBrother = False
   '
   '  Get Father
   '
   Call GetFather(oMyProduct,oFatherProduct)
   
   If  oMyProduct is oFatherProduct then 
       set oBrotherProduct = Nothing
       LOtherBrother = False   
   Else
       iPrevious = Currentlevel - 1
       call ScanNode(oFatherProduct, cChildren, NBChildren)
        
       if (NBChildren > 0) Then
         NbFilsAVisiter = arrayOfVisitedNode(iPrevious)
         NbFilsAVisiter = NbFilsAVisiter + 1
         If (NbFilsAVisiter <= NBChildren) Then
           LOtherBrother = True 
           iOther = 1 
         Else
           LOtherBrother = False 
         End If 
      Else
         LOtherBrother = False    
      End If

  End If  
  
  lExistBrother = LOtherBrother

End Function
' ----------------------------------------------------------------------------------------------
' NextBrother 
' ----------------------------------------------------------------------------------------------
Sub NextBrother(oMyProduct As Product, oBrotherProduct As Product,ilevel As Integer) 

  Dim NBChildren As Integer
  Dim iPrevious As Integer 
  Dim oFatherProduct As Product
  Dim NbFilsVisites As Integer 
  Dim cChildren As Products
  '
  ' Get Father
  '
  Call GetFather(oMyProduct,oFatherProduct)
  '
  If  oMyProduct is oFatherProduct then 
    Set oBrotherProduct = Nothing
  Else
    iPrevious = ilevel - 1
    Call ScanNode(oFatherProduct, cChildren, NBChildren)
       
    If (NBChildren > 0) Then
      NbFilsVisites = arrayOfVisitedNode(iPrevious)
      NbFilsVisites = NbFilsVisites + 1
      If NbFilsVisites <= NBChildren Then
        Set oBrotherProduct = cChildren.Item(NbFilsVisites)
        arrayOfVisitedNode(iPrevious) = NbFilsVisites
      Else
        Set oBrotherProduct=Nothing
      End If 
    Else
      Set oBrotherProduct=Nothing   
    End If

  End If
  
End Sub 
' ----------------------------------------------------------------------------------------------
' GetFather 
' ----------------------------------------------------------------------------------------------
Sub GetFather(oMyProduct As Product,OFather As Product)

    Dim GreatFather As Product 
    Dim ParentObject As AnyObject
    Set ParentObject = oMyProduct.Parent
    Set GreatFather = ParentObject.Parent
    Dim sType As String 

    sType = ParentObject.Name  
        
    If (sType = "Products") Then
      Set GreatFather = ParentObject.Parent                
      Set OFather = GreatFather 
    Else
      Set OFather = oMyProduct
    End If
    
End Sub

' ----------------------------------------------------------------------------------------------
' PrintInfo
' ----------------------------------------------------------------------------------------------
Sub PrintInfo(oMyProduct As Product)

  Dim sLF As String
  sLF = Chr(10) 

  If (Not (oMyProduct Is Nothing)) Then
    oReport.Write   oMyProduct.Name 
    oReport.Write   "             ; "
    oReport.Write   "             ; "
    oReport.Write   "               " &  sLF
  End If

End Sub

' ----------------------------------------------------------------------------------------------
' PrintHeader
' ----------------------------------------------------------------------------------------------
Sub PrintHeader(oMyDoc As Document)

  Dim sLF As String
  sLF = Chr(10) 
  Dim MyDate As Variant
  MyDate = Now

  If Not (oMyDoc Is Nothing ) Then
    oReport.Write "# Date : " & MyDate                      & sLF
    oReport.Write "# SCAN RESULT "                          & sLF
    oReport.Write "# Input Document  :       "              & sLF
    oReport.Write "# " &   oMyDoc.FullName                  & sLF
    oReport.Write "# "                                      & sLF
  End If

End Sub

' ----------------------------------------------------------------------------------------------
' PrintFoot
' ----------------------------------------------------------------------------------------------
Sub PrintFoot ()

  Dim sLF As String
  sLF = Chr(10) 
  oReport.Write "#  "                                 &  sLF 
  oReport.Write "########  Report file end  ########" &  sLF
  
End Sub
