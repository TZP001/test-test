'====================================================================================
' COPYRIGHT DASSAULT SYSTEMES  1999
'====================================================================================
'
' PSLNomenAccessFeat.CATScript
'
'====================================================================================
' Language="VBSCRIPT"
'
'
' Description:
' Access the user nomenclature hierachy from the
' CATArrangementNomenclature.feat as defined in a PSL/LND workbench 
' (.CATProduct document) using CATArrangementInterfaces IDL and report that
' in a EXCEL file
'
'====================================================================================
' Audit Trail:
'--------------------------------------------------------------------
'   Author     : Vic Szeto 
'   Date       : 8/1999
'   Chg id     :
'   Chg nature :
'--------------------------------------------------------------------
'   Modified   :
'   Date       : 
'   Chg id     :
'   Chg nature : 
'====================================================================================

Option Explicit

'// ---------- Debug Traces
Const intG_TRACEON = 1
Dim strMessage

'// ---------- Recursive level 
Dim intRecursiveLevel

'// ---------- objEXCEL application objects
Dim objEXCELapp As Object
Dim objEXCELwkBks As Object
Dim objEXCELwkBk As Object
Dim objEXCELwkShs As Object
Dim objEXCELSh As Object

'// ---------- objEXCEL Report Format
'// Row
Const intReportStartAfterRow = 0
'// Column
Const intReportIntClassName = 1
Const intReportStartAfterColumn = 1

Dim intReportCurrentRow
Dim intReportCurrentColumn

'@@@@@@@@@@@@@@@@@@@@@@@@@@@@@@@@@@@@@@@@@@@@@@@@@@@@@@@@@@@@@@@@@@@@@@@@@@@@@@@@@@@@
' The following environment variables for the path name must be modified
' according to the run time environment.
'@@@@@@@@@@@@@@@@@@@@@@@@@@@@@@@@@@@@@@@@@@@@@@@@@@@@@@@@@@@@@@@@@@@@@@@@@@@@@@@@@@@@
'====================================================================================
'  Define the EXCEL template file name here
'====================================================================================
Const strEXCELTemplateFileName = "C:\temp\PSLNomenAccessFeatTemplate.xls"

'----------OUTPUT TEMP DIRECTORY
Const strGOutputDirName = "C:\Temp"

' Above is the GLOBAL variable declarations section
'@@@@@@@@@@@@@@@@@@@@@@@@@@@@@@@@@@@@@@@@@@@@@@@@@@@@@@@@@@@@@@@@@@@@@@@@@@@@@@@@@@@@

'------------------------------------------------------------------------------------
Sub DbgTrace (iStrMsgString, iIntYesError)
'------------------------------------------------------------------------------------
If (intG_TRACEON = 1) Then
  CATIA.SystemService.Print iStrMsgString 
  If (iIntYesError = 1) Then CATIA.SystemService.Print "Err Number = " & Err.Number
End If

End Sub '/////////////////////////////////////////////////////////// DbgTrace


'========================================================================
Sub Copy_Files(strFileToCopy)
'========================================================================

 Dim strCATCommandPath           As String
 Dim strNewFilePath              As String
 Dim intSemiColonLocation        As Integer
 Dim strDefaulLocationOfTemplate As String
 Dim AppliFileSys                As FileSystem
   
   On Error Resume Next
   strCATCommandPath = CATIA.SystemService.Environ("CATCommandPath")  
   
   intSemiColonLocation  = Instr(3, strCATCommandPath, ";")  
          
   Set AppliFileSys = CATIA.FileSystem
   strDefaulLocationOfTemplate = ""
   strNewFilePath              = strGOutputDirName + "\" + strFileToCopy
   'CATIA.SystemService.Print strCATCommandPath

   If (intSemiColonLocation > 0) Then    
      Do While (intSemiColonLocation > 0)

        intSemiColonLocation = intSemiColonLocation -1
        strDefaulLocationOfTemplate = Left(strCATCommandPath, intSemiColonLocation) _
                                    + "\" + strFileToCopy

        If (AppliFileSys.FileExists(strDefaulLocationOfTemplate)) Then
          Exit Do 
        End If

        Err.Clear
        intSemiColonLocation =  intSemiColonLocation + 2
        strCATCommandPath = Mid(strCATCommandPath, intSemiColonLocation)
        intSemiColonLocation  = Instr(3, strCATCommandPath, ";")

        'CATIA.SystemService.Print strCATCommandPath
        'DbgTrace "intSemiColonLocation :" & intSemiColonLocation, 0

      Loop     ' Exit outer loop immediately.
   Else
      strDefaulLocationOfTemplate = strCATCommandPath + "\" + strFileToCopy
   End If
  
   AppliFileSys.CopyFile strDefaulLocationOfTemplate, strNewFilePath, true

   If (Not(AppliFileSys.FileExists(strNewFilePath))) Then
     Dim strMessage
     strMessage  = "Error Copying Template File:" + strDefaulLocationOfTemplate + "to " + strGOutputDirName + Chr(13)
     strMessage  = strMessage + Chr(13) + "Check the following...." + Chr(13)
     strMessage  = strMessage + "(1)Template File has read-write capability" + Chr(13)
     strMessage  = strMessage + "(2)Template File path is valid"
     msgbox (strMessage)    
     Exit Sub
   End If

End Sub '/////////////////////////////////////////////////////////// Copy_Files


'------------------------------------------------------------------------------------
Sub StartEXCEL ()
'------------------------------------------------------------------------------------
  Err.Clear
  On Error Resume Next
  Set objEXCELapp = GetObject (,"EXCEL.Application")  
  If Err.Number <> 0 Then   
     Err.Clear
     Set objEXCELapp = CreateObject ("EXCEL.Application")
  End If

  objEXCELapp.Application.Visible = TRUE
  Set objEXCELwkBks = objEXCELapp.Application.WorkBooks

  Copy_Files ("PSLNomenAccessFeatTemplate.xls")

  Err.Clear
  Set objEXCELwkBk  = objEXCELwkBks.Add (strEXCELTemplateFileName)

  If Err.Number <> 0 Then
     Dim strMessage
     strMessage  = "Error Loading Template File:" + strEXCELTemplateFileName + Chr(13)
     strMessage  = strMessage + Chr(13) + "Check the following...." + Chr(13)
     strMessage  = strMessage + "(1)Template File has read-write capability" + Chr(13)
     strMessage  = strMessage + "(2)Template File path is valid"
	   msgbox (strMessage)
     Err.Clear
  End If

  Set objEXCELwkShs = objEXCELwkBk.Worksheets
  Set objEXCELSh = objEXCELwkBk.Sheets ("User Nomenclature") 

'//--------- No show the first column (internal class name)
objEXCELSh.Columns("A:A").ColumnWidth = 0.0

End Sub '/////////////////////////////////////////////////////////// StartEXCEL

'------------------------------------------------------------------------------------
Sub EndEXCEL ()
'------------------------------------------------------------------------------------
objEXCELwkBk.Close

End Sub '/////////////////////////////////////////////////////////// EndEXCEL

'------------------------------------------------------------------------------------
Sub WriteToEXCEL (iIntRow, iIntColumn, iStr)
'------------------------------------------------------------------------------------
If ( (iIntRow > 0) And (iIntColumn > 0) ) Then
   objEXCELSh.Cells (iIntRow, iIntColumn) = iStr
   objEXCELSh.Cells (iIntRow, iIntColumn).Select
End If

End Sub '/////////////////////////////////////////////////////////// WriteToEXCEL

'------------------------------------------------------------------------------------
Sub WriteInternalDataToEXCEL (iIntRow, iIntColumn, iStr)
'------------------------------------------------------------------------------------
If ( (iIntRow > 0) And (iIntColumn > 0) ) Then
   'objEXCELSh.Cells(iIntRow,iIntColumn).ClearComments
   objEXCELSh.Cells(iIntRow,iIntColumn).AddComment iStr
   objEXCELSh.Cells(iIntRow,iIntColumn).Comment.Visible = FALSE
   DbgTrace objEXCELSh.Cells(iRow,iColumn).Comment.Text, 0
End If

End Sub '/////////////////////////////////////////////////////////// WriteInternalDataToEXCEL

'------------------------------------------------------------------------------------
Sub Recursive_Browse (iobjArrNomen)
'------------------------------------------------------------------------------------
Dim objArrSubTypes As ArrNomenclatures
Dim strIconName
Dim strIntSysClassName
Dim strNLSInstanceName
Dim strSuperTypeName
Dim intNBOfNom
Dim intWriteAtColumn
Dim intSaveRecursiveLevel

'// --------- Initialize output information
intNBOfNom = 0
strIconName = ""
strIntSysClassName = ""
strNLSInstanceName = ""
strSuperTypeName = ""

On Error Resume Next

Set objArrSubTypes = iobjArrNomen.SubTypes
If (Err.Num = 0) Then
   intNBOfNom = objArrSubtypes.Count
   strMessage = "Subtypes.count = " & intNBOfNom
   DbgTrace strMessage,0 
End If

'//----------  Recursively list all sub-types
If (intNBOfNom > 0) Then
   intRecursiveLevel = intRecursiveLevel + 1

   '--------------------------------------------------------------------------------
   '  intRecursiveLevel is being increased as we travel down the tree
   '  we need to save the current level to write the "siblings" of the current
   '  node, when we are back to the current level
   '--------------------------------------------------------------------------------
   intSaveRecursiveLevel = intRecursiveLevel
   Dim intJ
   Dim objJArrNom As ArrNomenclature
   For intJ=1 to intNBOfNom  
     strIntSysClassName = ""
     Set objJArrNom = objArrSubTypes.Item(intJ) 
     If (Err.Num = 0) Then       
       strNLSInstanceName = objJArrNom.NLSInstanceName
       If (Err.Num = 0) Then 

           intWriteAtColumn = intReportStartAfterColumn + intSaveRecursiveLevel

		       strMessage = "child = " & strNLSInstanceName & " is put at column " & _
		                 intWriteAtColumn & " when level = " & intSaveRecursiveLevel
           DbgTrace strMessage, 0

           ' Write NLS Name
           ' ---------------------------
	          intReportCurrentRow = intReportCurrentRow + 1
	          WriteToEXCEL intReportCurrentRow, intWriteAtColumn, strNLSInstanceName

           ' Write Internal System Name
           ' ---------------------------
           If(objJArrNom.IsSystemNomenclature) Then
              strIntSysClassName = objJArrNom.IntSysClassName
              WriteToEXCEL intReportCurrentRow, intReportIntClassName, strIntSysClassName
           End If

           ' Write Icon Name
           ' ---------------------------
		       strIconName = objJArrNom.IconName
           If (Err.Num = 0) Then
               WriteInternalDataToEXCEL _
			         intReportCurrentRow, intWriteAtColumn,strIconName		                                 
           End If  
       End If 
 
       '------------------------------------------------------------------------------
       '  intRecursiveLevel should starts from the current node level.
       '  It might have been increased from going down the previous sibling nodes
       '------------------------------------------------------------------------------ 
	   intRecursiveLevel =  intSaveRecursiveLevel  
	    
       Recursive_Browse objJArrNom

	 End If 'objArrSubTypes is good

   Next 'For intJ=1 to intNBOfNom
End If

End Sub '/////////////////////////////////////////////////////////// Recursive_Browse

'====================================================================================
Sub CATMain ()
'====================================================================================

StartEXCEL

Dim objDocument0 As Object

Set objDocument0 = CATIA.ActiveDocument
DbgTrace "ActiveDocument",1

Dim objArrWorkbench1 As Workbench
Set objArrWorkbench1 = objDocument0.GetWorkbench  ( "ArrWorkbench" ) 
DbgTrace "GetWorkbench",1

Dim objArrNomTree1 As ArrNomenclatureTree
Set objArrNomTree1 = objArrWorkbench1.ArrNomenclatureTree
DbgTrace "get_ArrNomenclatureTree",1

Dim objArrNomTopNode As ArrNomenclatures
Set objArrNomTopNode = objArrNomTree1.BaseNomenclatures
DbgTrace "get_BaseNomenclatures",1

Dim intNBOfNom 
intNBOfNom = objArrNomTopNode.Count
strMessage = "Count = " & intNBOfNom
DbgTrace strMessage,1

'//
'//
'//    Recursively Loop Through each nomenclature
'//

intReportCurrentRow = intReportStartAfterRow
Dim intK
Dim objKArrNom As ArrNomenclature
Dim strIntSysClassName
Dim strNLSInstanceName
Dim strIconName

For intK=1 to intNBOfNom

   On Error Resume Next

   DbgTrace "****************************************************",0
   strMessage = "Member = " & intK
   DbgTrace strMessage,0
   
   intReportCurrentRow = intReportCurrentRow + 1 

   strIntSysClassName = ""
   strNLSInstanceName = ""
   strIconName = ""

   Set objKArrNom = objArrNomTopNode.Item(intK)

   strIntSysClassName = objKArrNom.IntSysClassName 
   If (Err.Num = 0) Then
      WriteToEXCEL _
	    intReportCurrentRow, intReportIntClassName, strIntSysClassName
   End If  

   '---------- There are some hidden columns
   '---------- before the intReportStartAfterColumn

   intReportCurrentColumn = intReportStartAfterColumn + 1
   strNLSInstanceName = objKArrNom.NLSInstanceName 
   If (Err.Num = 0) Then
      WriteToEXCEL _
	    intReportCurrentRow, intReportCurrentColumn, strNLSInstanceName
   End If  

   strIconName = objKArrNom.IconName
   If (Err.Num = 0) Then
      WriteInternalDataToEXCEL intReportCurrentRow, _
	    intReportCurrentColumn, strIconName
   End If  

   intRecursiveLevel = 1
   Recursive_Browse objKArrNom

Next '//K to NBOfNom

'--------- EndExcel

End Sub '/////////////////////////////////////////////////////////// CATMain
