'// COPYRIGHT DASSAULT SYSTEMES  1999
'//============================================================================
'//
'// Language="VBSCRIPT"
'// This CATScript allows the user to extract Tubing Data from BendableString
'// objects created in the Systems Routing Product
'// ----------------- ASSUMPTIONS----------------------------------------------
'// This CATScript assumes that the user has selected BendableString objects
'// from the CATIA Specification Viewer or the 3D Window.
'// ------------------- WARNING------------------------------------------------
'// It is advised that the user understand the VBScript and VBA concepts before
'// attempting to modify the code to suit their needs. Microsoft Excel 97 
'// provides excellent documentation on the use of VBScript and VBA.
'// ------------------ HOW TO CUSTOMIZE----------------------------------------
'// The tubic extraction logic described here in this CATScript is only meant
'// as a template and is expected that the user will fine-tune this template
'// to suit their specific needs.
'//
'// If you are not familiar with writing VBScripts, then we suggest that you
'// execute this template macro once (before attempting to modify) so as to
'// understand the logic involved. Please note that we have provided a Debug
'// utility for your assistance.
'//
'// If you would like to simply change the titles of the columns, please 
'// modify the contents of the string variables in the "User Customizable Section".
'// Modify only the string variables that have the name "User". For example,
'// you could modify strGReportLabelCurUnitUserLabel's contents to be 
'// " Session Linear Unit: " instead of the default " Current Linear Unit: ".
'//============================================================================
'// Major CATIA interface used:
'//
'// interface                  VB Name          Remarks
'// -----------               ------------      --------------
'// CATIADocument             Document          access the current document
'// CATIAWorkbench            workbench         access the Manufacturing Systems 
'//                                             Layout workbench, 
'//                                             calculate footprint,
'//                                             get the current user units ...
'// CATIASelection            Selection         to get the object from CSO in the 
'//                                             interactive section
'// CATIAArrBendableString    ArrBendableString to get the Tubing Object and its info 
'//
'//============================================================================
'//
'// Audit Trail:
'//----------------------------------------------------------------------------
'//   Author     : Sudhi Gulur (Dassault Systemes of America)
'//   Date       : January 2000 
'//   Chg id     :
'//   Chg nature :
'//----------------------------------------------------------------------------
'//   Modified   : Atul Deodhar (Dassault Systemes of America)
'//   Date       : October 2005
'//   Chg id     :
'//   Chg nature : RI 514277 - Rotation angle position and sign, Slope Angle sign
'//============================================================================

Option Explicit

'******************************************************************************
'  GLOBAL variable declarations section
'******************************************************************************
'// ---------- Debug Traces
Const intG_TRACEON = 1
Dim strMessage

'//---------- EXCEL application 
Dim objGEXCELapp As Object
Dim objGEXCELwkBks As Object
Dim objGEXCELwkBk As Object
Dim objGEXCELwkShs As Object
Dim objGEXCELSh As Object

'// ---------- CATIAV5 application objects
Dim objCATIAV5Document0 As Document
Dim objCATIAV5ArrWorkbench0 As Workbench
Dim objCATIAV5Selection As Selection

Dim intGReportCurrentRow  
Dim intGReportMaxColumnIndex
Dim dblGTotalLength


'@@@@@@@@@@@@@@@@@@@@@@@@@@@@@@@@@@@@@@@@@@@@@@@@@@@@@@@@@@@@@@@@@@@@@@@@@@@@@@
'//                       User customizable sections                  
'@@@@@@@@@@@@@@@@@@@@@@@@@@@@@@@@@@@@@@@@@@@@@@@@@@@@@@@@@@@@@@@@@@@@@@@@@@@@@@

'//---------- EXCEL report format
Const strGReportLabelCurUnit                = "Current Unit"
Const strGReportLabelCurUnitUserLabel       = " Current Linear  Unit: "
Const strGReportLabelCurAngUnitUserLabel    = " Current Angular Unit: "
Const intGReportCurUnitCol                  = 1
Const strGReportLabelCurUnitValue           = "Current Unit Value"

Const strGReportLabelBendStrIndex           = "Element Name"
Const strGReportLabelBendStrIndexUserLabel  = "Element Name"
Const intGReportBendStrIndexCol             = 2
Const strGReportLabelBendStrIndexValue      = "BendableString Index Value"

Const strGReportLabelSegmentIndex           = "Node Index"
Const strGReportLabelSegmentIndexUserLabel  = " Node Index. "
Const intGReportSegmentIndexCol             = 3

Const strGReportLabelXCoord                 = "X"
Const strGReportLabelXCoordUserLabel        = " X "
Const intGReportStartXCoordCol              = 4

Const strGReportLabelYCoord                 = "Y"
Const strGReportLabelYCoordUserLabel        = " Y "
Const intGReportStartYCoordCol              = 5

Const strGReportLabelZCoord                 = "Z"
Const strGReportLabelZCoordUserLabel        = " Z "
Const intGReportStartZCoordCol              = 6

Const strGReportLabelSegmentLength          = "Segment Length"
Const strGReportLabelSegmentLengthUserLabel = " Segment Length "
Const intGReportSegmentLengthCol            = 7

Const strGReportLabelTotalLength            = "Total Length"
Const strGReportLabelTotalLengthUserLabel   = " Total Length "
Const intGReportTotalLengthCol              = 8

Const strGReportLabelBendRadius             = "Bend Radius"
Const strGReportLabelBendRadiusUserLabel    = " Bend Radius "
Const intGReportBendRadiusCol               = 9

Const strGReportLabelBendAngle              = "Bend Angle"
Const strGReportLabelBendAngleUserLabel     = " Bend Angle "
Const intGReportBendAngleCol                = 10

Const strGReportLabelRotation               = "Rotation Angle"
Const strGReportLabelRotationUserLabel      = " Rotation Angle "
Const intGReportRotationCol                 = 11

Const strGReportLabelSlopeAngle             = "Slope Angle"
Const strGReportLabelSlopeAngleUserLabel    = " Slope Angle "
Const intGReportSlopeAngleCol               = 12

intGReportMaxColumnIndex                    = intGReportSlopeAngleCol

'//Light yellow (please refer to Excel Color Table)
Const intUserEXCELRowColor                  = 19 

'========== EXCEL template direction path
Const strGReportTemplate = "C:\temp\PSLTubingExtractTemplate.xls" 

'----------OUTPUT TEMP DIRECTORY
Const strGOutputDirName = "C:\Temp"

'---------- must name the sheet in the template accordingly
Const strGReportEXCELSheetName = "Tubing Data Sheet"

'@@@@@@@@@@@@@@@@@@@@@@@@@@@@@@@@@@@@@@@@@@@@@@@@@@@@@@@@@@@@@@@@@@@@@@@@@@@@@@

'******************************************************************************
Sub DbgTrace (iStrMsgString, iIntYesError)
'******************************************************************************
If (intG_TRACEON = 1) Then
  CATIA.SystemService.Print iStrMsgString 
  If (iIntYesError = 1) Then 
	   CATIA.SystemService.Print "Err Number = " & Err.Number
	End If
End If

End Sub '///////////////////////////////////////////////////////////// DbgTrace

'========================================================================
Sub Copy_Files(strFileToCopy)
'========================================================================

 Dim strCATCommandPath           As String
 Dim strNewFilePath              As String
 Dim intSemiColonLocation        As Integer
 Dim strDefaulLocationOfTemplate As String
 Dim AppliFileSys                As FileSystem
   
   On Error Resume Next
   strCATCommandPath = CATIA.SystemService.Environ("CATCommandPath")  
   
   intSemiColonLocation  = Instr(3, strCATCommandPath, ";")  
          
   Set AppliFileSys = CATIA.FileSystem
   strDefaulLocationOfTemplate = ""
   strNewFilePath              = strGOutputDirName + "\" + strFileToCopy
   'CATIA.SystemService.Print strCATCommandPath

   If (intSemiColonLocation > 0) Then    
      Do While (intSemiColonLocation > 0)

        intSemiColonLocation = intSemiColonLocation -1
        strDefaulLocationOfTemplate = Left(strCATCommandPath, intSemiColonLocation) _
                                    + "\" + strFileToCopy

        If (AppliFileSys.FileExists(strDefaulLocationOfTemplate)) Then
          Exit Do 
        End If

        Err.Clear
        intSemiColonLocation =  intSemiColonLocation + 2
        strCATCommandPath = Mid(strCATCommandPath, intSemiColonLocation)
        intSemiColonLocation  = Instr(3, strCATCommandPath, ";")

        'CATIA.SystemService.Print strCATCommandPath
        'DbgTrace "intSemiColonLocation :" & intSemiColonLocation, 0

      Loop     ' Exit outer loop immediately.
   Else
      strDefaulLocationOfTemplate = strCATCommandPath + "\" + strFileToCopy
   End If
  
   AppliFileSys.CopyFile strDefaulLocationOfTemplate, strNewFilePath, true

   If (Not(AppliFileSys.FileExists(strNewFilePath))) Then
     Dim strMessage
     strMessage  = "Error Copying Template File:" + strDefaulLocationOfTemplate + "to " + strGOutputDirName + Chr(13)
     strMessage  = strMessage + Chr(13) + "Check the following...." + Chr(13)
     strMessage  = strMessage + "(1)Template File has read-write capability" + Chr(13)
     strMessage  = strMessage + "(2)Template File path is valid"
     msgbox (strMessage)    
     Exit Sub
   End If

End Sub '/////////////////////////////////////////////////////////// Copy_Files


'******************************************************************************
Sub StartEXCEL()
'******************************************************************************
  Err.Clear
  On Error Resume Next
  Set objGEXCELapp = GetObject (,"EXCEL.Application")  
  If Err.Number <> 0 Then   
     Err.Clear
     Set objGEXCELapp = CreateObject ("EXCEL.Application")
  End If

  objGEXCELapp.Application.Visible = TRUE
  Set objGEXCELwkBks = objGEXCELapp.Application.WorkBooks

  Copy_Files ("PSLTubingExtractTemplate.xls")

  Err.Clear
  Set objGEXCELwkBk = objGEXCELwkBks.Add (strGReportTemplate)
  If Err.Number <> 0 Then
     Dim strMessage
     strMessage  = "Error Loading Template File:" + strGReportTemplate + Chr(13)
     strMessage  = strMessage + Chr(13) + "Check the following...." + Chr(13)
     strMessage  = strMessage + "(1)Template File has read-write capability" + Chr(13)
     strMessage  = strMessage + "(2)Template File path is valid"
	   msgbox (strMessage)
     Err.Clear
  End If
  Set objGEXCELwkShs = objGEXCELwkBk.Worksheets
  Set objGEXCELSh = objGEXCELwkBk.Sheets (strGReportEXCELSheetName)
  objGEXCELSh.Select
End Sub '/////////////////////////////////////////////////////////// StartEXCEL

'******************************************************************************
Sub WriteColumnTitles()
'******************************************************************************
  '//==========================================================================
  '// Write out the column headers
  '//==========================================================================
  Dim intLReportHeadingCurRow

  intGReportCurrentRow = intGReportCurrentRow + 1
  intLReportHeadingCurRow = intGReportCurrentRow

  Dim intLUnitIndexColum 

  intLUnitIndexColum = intGReportCurUnitCol + 1
  objGEXCELSh.Columns(intGReportCurUnitCol).Style.NumberFormat = "@"
  objGEXCELSh.Columns(intLUnitIndexColum).Style.NumberFormat = "@"

  WriteToEXCEL intGReportCurrentRow, strGReportLabelBendStrIndex, _ 
               strGReportLabelBendStrIndexUserLabel,1,1,1,1

  objGEXCELSh.Columns(intGReportSegmentIndexCol).Style.NumberFormat = "@"
  WriteToEXCEL intLReportHeadingCurRow, strGReportLabelSegmentIndex, _
               strGReportLabelSegmentIndexUserLabel, 1,1,1,1

  objGEXCELSh.Columns(intGReportStartXCoordCol).Style.NumberFormat = "0.0000"
  WriteToEXCEL intLReportHeadingCurRow, strGReportLabelXCoord, _
               strGReportLabelXCoordUserLabel, 1,1,1,1

  objGEXCELSh.Columns(intGReportStartYCoordCol).Style.NumberFormat = "0.0000"
  WriteToEXCEL intLReportHeadingCurRow, strGReportLabelYCoord, _
               strGReportLabelYCoordUserLabel, 1,1,1,1

  objGEXCELSh.Columns(intGReportStartZCoordCol).Style.NumberFormat = "0.0000"
  WriteToEXCEL intLReportHeadingCurRow, strGReportLabelZCoord, _
               strGReportLabelZCoordUserLabel, 1,1,1,1

  objGEXCELSh.Columns(intGReportSegmentLengthCol).Style.NumberFormat = "0.0000"
  WriteToEXCEL intLReportHeadingCurRow, strGReportLabelSegmentLength, _
               strGReportLabelSegmentLengthUserLabel, 1,1,1,1

  objGEXCELSh.Columns(intGReportTotalLengthCol).Style.NumberFormat = "0.0000"
  WriteToEXCEL intLReportHeadingCurRow, strGReportLabelTotalLength, _
               strGReportLabelTotalLengthUserLabel, 1,1,1,1

  objGEXCELSh.Columns(intGReportBendRadiusCol).Style.NumberFormat = "0.0000"
  WriteToEXCEL intLReportHeadingCurRow, strGReportLabelBendRadius, _
               strGReportLabelBendRadiusUserLabel, 1,1,1,1

  objGEXCELSh.Columns(intGReportBendAngleCol).Style.NumberFormat = "0.0000"
  WriteToEXCEL intLReportHeadingCurRow, strGReportLabelBendAngle, _
               strGReportLabelBendAngleUserLabel, 1,1,1,1

  objGEXCELSh.Columns(intGReportRotationCol).Style.NumberFormat = "0.0000"
  WriteToEXCEL intLReportHeadingCurRow, strGReportLabelRotation, _
               strGReportLabelRotationUserLabel, 1,1,1,1

  objGEXCELSh.Columns(intGReportSlopeAngleCol).Style.NumberFormat = "0.0000"
  WriteToEXCEL intLReportHeadingCurRow, strGReportLabelSlopeAngle, _
               strGReportLabelSlopeAngleUserLabel, 1,1,1,1

  intGReportCurrentRow = intGReportCurrentRow + 1
  InsertARowAt (intGReportCurrentRow)
End Sub'/////////////////////////////////////////////////////////// WriteColumnTitles

'******************************************************************************
Sub ArrangeExcelColumns ()
'******************************************************************************
 Dim iIndex

 'DbgTrace "Attempting to Arrange Columns", 0
 For iIndex = 1 to intGReportMaxColumnIndex
   'DbgTrace "Arranging Column:" & iIndex, 0
   objGEXCELSh.Columns(iIndex).EntireColumn.AutoFit
 Next

End Sub '//////////////////////////////////////////////////////// ArrangeExcelColumns


'******************************************************************************
Sub EndEXCEL ()
'******************************************************************************
  objGEXCELwkBk.Close
  objGEXCELapp.Quit
End Sub '///////////////////////////////////////////////////////////// EndEXCEL

'******************************************************************************
Sub InsertARowAt (iIntRow)
'******************************************************************************
  objGEXCELSh.Cells(iIntRow,1).EntireRow.Select
  objGEXCELapp.Selection.Insert
  objGEXCELSh.Cells(iIntRow,1).EntireRow.Select
  objGEXCELSh.Rows(iIntRow).Interior.ColorIndex = intUserEXCELRowColor
End Sub '////////////////////////////////////////////////////// InsertARowAt


'******************************************************************************
Sub StartCATIAV5 ()
'******************************************************************************
  Set objCATIAV5Document0 = CATIA.ActiveDocument
  DbgTrace "V5: Active Document",1

  '//---------- Get Arrworkbench from current document
  Set objCATIAV5ArrWorkbench0 = objCATIAV5Document0.GetWorkbench("ArrWorkbench") 
  DbgTrace "V5: GetWorkbench0",1

  '//---------- Get current selection
  Set objCATIAV5Selection = objCATIAV5Document0.Selection
  DbgTrace "V5: Selection",1

End Sub '///////////////////////////////////////////////////////// StartCATIAV5

'******************************************************************************
Sub WriteToEXCEL (iRow, iLabel, iString, iBold, iLargeSize, iFill, iItalic)
'******************************************************************************
  Dim WhichColumn
  WhichColumn = 0

  Select Case iLabel
      Case strGReportLabelSegmentIndex
         WhichColumn = intGReportSegmentIndexCol
      Case strGReportLabelXCoord
         WhichColumn = intGReportStartXCoordCol
      Case strGReportLabelYCoord
         WhichColumn = intGReportStartYCoordCol
      Case strGReportLabelZCoord
         WhichColumn = intGReportStartZCoordCol
      Case strGReportLabelSegmentLength
         WhichColumn = intGReportSegmentLengthCol
      Case strGReportLabelTotalLength
         WhichColumn = intGReportTotalLengthCol
      Case strGReportLabelBendRadius
         WhichColumn = intGReportBendRadiusCol
      Case strGReportLabelBendAngle
         WhichColumn = intGReportBendAngleCol
      Case strGReportLabelRotation
         WhichColumn = intGReportRotationCol
      Case strGReportLabelSlopeAngle
         WhichColumn = intGReportSlopeAngleCol
      Case strGReportLabelBendStrIndex
         WhichColumn = intGReportBendStrIndexCol
      Case strGReportLabelBendStrIndexValue
        WhichColumn = intGReportBendStrIndexCol
      Case strGReportLabelCurUnit
         WhichColumn = intGReportCurUnitCol     
      Case strGReportLabelCurUnitValue
         WhichColumn = intGReportCurUnitCol + 1          
  End Select

  If (WhichColumn > 0) Then
     If (iBold > 0) Then
        objGEXCELSh.Cells(iRow,WhichColumn).Font.Bold = True
     Else
        objGEXCELSh.Cells(iRow,WhichColumn).Font.Bold = False
     End If
     If (iLargeSize > 0) Then
        objGEXCELSh.Cells(iRow,WhichColumn).Font.Size = 12
     Else
        objGEXCELSh.Cells(iRow,WhichColumn).Font.Size = 10
     End If
     If (iFill > 0) Then
       objGEXCELSh.Cells(iRow,WhichColumn).Interior.ColorIndex = 9 '//Brown background
       objGEXCELSh.Cells(iRow,WhichColumn).Font.ColorIndex = 2 '// White font 
     Else 
       objGEXCELSh.Cells(iRow,WhichColumn).Interior.ColorIndex = intUserEXCELRowColor
       objGEXCELSh.Cells(iRow,WhichColumn).Font.ColorIndex = 9 '// White font 
     End If
     objGEXCELSh.Cells (iRow,WhichColumn) = iString
  End If

End Sub '///////////////////////////////////////////////////////// WriteToEXCEL

'******************************************************************************
Sub ColorEntireCurrentRow(iRow )
'******************************************************************************
  '//=======================================================================
  '// Set the Entire Row Color and then Override below with Specific Colors
  '//=======================================================================
  objGEXCELSh.Rows(iRow).Interior.ColorIndex = intUserEXCELRowColor

End Sub'/////////////////////////////////////////////////////////ColorEntireCurrentRow


'******************************************************************************
Sub ExtractTubingData(iObjBendableString)
'//===========================================================================
'// Check the Radius of the segment, to see if it is an arc segment. If it
'// is, only then fetch the BendNodeXCoords, BendNodeXCoords, BendNodeXCoords.
'// Otherwise, it is a straight segment.
'//
'//===========================================================================
'******************************************************************************
  Dim intNumOfSegments As integer
  Dim dblStrXCoord
  Dim dblStrYCoord
  Dim dblStrZCoord
  Dim dblEndXCoord
  Dim dblEndYCoord
  Dim dblEndZCoord
  Dim dblBendNodeXCoord
  Dim dblBendNodeYCoord
  Dim dblBendNodeZCoord

  Dim dblSegLength
  Dim dblBendAngle   
  Dim dblBendRadius  
  Dim dblRotationAngle
  Dim dblSlopeAngle
  Dim intK
  Dim PointIndex
  Dim PrevSegType
  Dim StrPointIndex 
  Dim dblSlopeAngleDiff  As double
  Dim dblPrevSlopeAngle  As double
  Dim dblSegmentData(14) As double
  Dim dblLinearSegLen    As double
  Dim dblArcLen          As double
  On Error Resume Next

  DbgTrace "ExtractTubingData", 0

  intNumOfSegments        = iObjBendableString.GetNumOfSegments
  DbgTrace "Number of Tubing Segments = " & intNumOfSegments, 0

  PointIndex  = 0
  dblGTotalLength   = 0.0
  dblSlopeAngleDiff = 0.0
  dblPrevSlopeAngle = 0.0

  intGReportCurrentRow = intGReportCurrentRow +1
  InsertARowAt (intGReportCurrentRow)

  If (intNumOfSegments > 0) Then

     For intK=1 to intNumOfSegments

       iObjBendableString.GetSegmentData intK, dblSegmentData

       dblStrXCoord        = dblSegmentData(0)
       dblStrYCoord        = dblSegmentData(1)
       dblStrZCoord        = dblSegmentData(2)

       dblEndXCoord        = dblSegmentData(3)
       dblEndYCoord        = dblSegmentData(4)
       dblEndZCoord        = dblSegmentData(5)

       '//Valid only if Radius > 0
       dblBendNodeXCoord   = dblSegmentData(6)
       dblBendNodeYCoord   = dblSegmentData(7)
       dblBendNodeZCoord   = dblSegmentData(8)

       '//Valid only if Radius > 0
       dblBendRadius       = dblSegmentData(9)
       dblBendAngle        = dblSegmentData(10)

       dblRotationAngle    = dblSegmentData(11)
       dblSlopeAngle       = dblSegmentData(12)

       dblLinearSegLen     = dblSegmentData(13)
       '//Arc Len valid only if Radius > 0
       dblArcLen           = dblSegmentData(14)

       '//=====================================
       '// Check if Linear Segment or Arc
       '//=====================================

       If (dblBendRadius > 0) Then
         PointIndex = PointIndex +1
         StrPointIndex = "# " & PointIndex & "."

         WriteToEXCEL  intGReportCurrentRow, strGReportLabelSegmentIndex, _
                     StrPointIndex, 0,0,0,0
         WriteToEXCEL  intGReportCurrentRow, strGReportLabelXCoord, _
                     dblBendNodeXCoord, 0,0,0,0
         WriteToEXCEL  intGReportCurrentRow, strGReportLabelYCoord, _
                     dblBendNodeYCoord, 0,0,0,0
         WriteToEXCEL  intGReportCurrentRow, strGReportLabelZCoord, _
                     dblBendNodeZCoord, 0,0,0,0
         WriteToEXCEL  intGReportCurrentRow, strGReportLabelSegmentLength, _
                     dblArcLen, 0,0,0,0
         WriteToEXCEL  intGReportCurrentRow, strGReportLabelBendRadius, _
                     dblBendRadius, 0,0,0,0
         WriteToEXCEL  intGReportCurrentRow, strGReportLabelBendAngle, _
                     dblBendAngle, 0,0,0,0
         WriteToEXCEL intGReportCurrentRow, strGReportLabelSlopeAngle, _
                    dblSlopeAngle, 0,0,0,0
        
         dblGTotalLength = dblGTotalLength + dblArcLen
       Else
         '//===================================
         '// Write Linear Segment Start Data
         '//===================================
         PointIndex = PointIndex +1
         StrPointIndex = "# " & PointIndex & "."
         WriteToEXCEL intGReportCurrentRow, strGReportLabelSegmentIndex, _
                    StrPointIndex, 0,0,0,0

         WriteToEXCEL intGReportCurrentRow, strGReportLabelXCoord, _
                    dblStrXCoord, 0,0,0,0
         WriteToEXCEL intGReportCurrentRow, strGReportLabelYCoord, _
                    dblStrYCoord, 0,0,0,0
         WriteToEXCEL intGReportCurrentRow, strGReportLabelZCoord, _
                    dblStrZCoord, 0,0,0,0
         WriteToEXCEL intGReportCurrentRow, strGReportLabelTotalLength, _
                    dblGTotalLength, 0,0,0,0
         If (1 = intK) Then
           WriteToEXCEL intGReportCurrentRow, strGReportLabelSlopeAngle, _
                    dblSlopeAngle, 0,0,0,0
         End If

         '//================================================
         '// Write Segment Length and Rotation Data
         '//================================================
         intGReportCurrentRow = intGReportCurrentRow +1
         InsertARowAt (intGReportCurrentRow)

         WriteToEXCEL    intGReportCurrentRow, strGReportLabelSegmentLength, _
                       dblLinearSegLen, 0,0,0,0

         If (0.0 = dblRotationAngle) Then
             dblRotationAngle = 0
         Else
             WriteToEXCEL  intGReportCurrentRow, strGReportLabelRotation, _
                       dblRotationAngle, 0,0,0,0
         End If

         '//============================
         '// Write Segment End Data
         '//============================
         intGReportCurrentRow = intGReportCurrentRow +1
         InsertARowAt (intGReportCurrentRow)

         PointIndex = PointIndex +1
         StrPointIndex = "# " & PointIndex & "."
       
         dblGTotalLength = dblGTotalLength + dblLinearSegLen

         WriteToEXCEL  intGReportCurrentRow, strGReportLabelSegmentIndex, _
                     StrPointIndex, 0,0,0,0
         WriteToEXCEL  intGReportCurrentRow, strGReportLabelXCoord, _
                     dblEndXCoord, 0,0,0,0
         WriteToEXCEL  intGReportCurrentRow, strGReportLabelYCoord, _
                     dblEndYCoord, 0,0,0,0
         WriteToEXCEL  intGReportCurrentRow, strGReportLabelZCoord, _
                     dblEndZCoord, 0,0,0,0
         WriteToEXCEL intGReportCurrentRow, strGReportLabelTotalLength, _
                     dblGTotalLength, 0,0,0,0
       End If

       '//==============================================
       '//
       '//==============================================
       intGReportCurrentRow = intGReportCurrentRow +1
       InsertARowAt (intGReportCurrentRow)
     Next '//For intK=2 to intNumOfSegments

     '// Write out the final total length
     If(dblGTotalLength > 0.0) Then
     WriteToEXCEL intGReportCurrentRow, strGReportLabelTotalLength, _
                 dblGTotalLength, 1,0,0,0
     End If

  End if '//If (intNumOfSegments > 0) Then

  intGReportCurrentRow = intGReportCurrentRow + 1
  InsertARowAt (intGReportCurrentRow)
End Sub '////////////////////////////////////////////////////////////// ExtractTubingData

'******************************************************************************
Sub CATMain()
'******************************************************************************

 '//================================================================================
 '//Define the variables needed in the Main program
 '//================================================================================
  Dim intNBInSelection  As integer
  Dim intSubProdIndex   As integer
  Dim objSysLineProduct As ArrSystemLineProduct
  Dim objBendableString As ArrBendableString

 '//================================================================================
 '// Execution Starts Here
 '//================================================================================
  intGReportCurrentRow = 12  '// Start on 10th Row after the image area

  StartEXCEL

  StartCATIAV5

  intNBInSelection     = 0
  dblGTotalLength      = 0.0

  On Error Resume Next

  Dim strCurrentLinearUnit
  Dim strCurrentAngularUnit
  strCurrentLinearUnit= objCATIAV5ArrWorkbench0.GetCurrentUnits("LENGTH")
  strCurrentAngularUnit = objCATIAV5ArrWorkbench0.GetCurrentUnits("ANGLE")

  '//===============================================================================
  '// Write out the Linear and Angular units in which data is going to be reported.
  '// Note that the units can be changed by selecting Tools->Options->General
  '// and then choosing the Units Tab Page.
  '//===============================================================================
  WriteToEXCEL  intGReportCurrentRow, strGReportLabelCurUnit, _
                strGReportLabelCurUnitUserLabel, 1,1 ,0,0
  WriteToEXCEL  intGReportCurrentRow, strGReportLabelCurUnitValue, _
                strCurrentLinearUnit, 1,1,0,0

  intGReportCurrentRow = intGReportCurrentRow +1
  InsertARowAt (intGReportCurrentRow)

  WriteToEXCEL  intGReportCurrentRow, strGReportLabelCurUnit, _
                strGReportLabelCurAngUnitUserLabel, 1,1 ,0,0
  WriteToEXCEL  intGReportCurrentRow, strGReportLabelCurUnitValue, _
                strCurrentAngularUnit, 1,1,0,0

  WriteColumnTitles

  intGReportCurrentRow = intGReportCurrentRow +1
  InsertARowAt (intGReportCurrentRow)
  '//===============================================================================
  ' Find from the selection list, objects that conform to the CATIAArrSystemLineProduct
  ' interface.
  '//===============================================================================

  Set objSysLineProduct = objCATIAV5Selection.FindObject("CATIAArrSystemLineProduct")
  DbgTrace "FindObject", 1

  if (Err.Number <> 0) Then 
    Set objSysLineProduct = Nothing
  Else
    Do Until ( objSysLineProduct Is Nothing )

       Dim intNumOfSubProducts As integer
       intNumOfSubProducts = objSysLineProduct.GetSubProductsCount("CATIAArrBendableString")
       DbgTrace "Number of Sub Bendable Objects :" & intNumOfSubProducts , 1
       
       If (intNumOfSubProducts > 0) Then
         For intSubProdIndex =1 to intNumOfSubProducts
             Set objBendableString = objSysLineProduct.GetSubItem(intSubProdIndex)
             If(objBendableString Is Nothing ) Then
               DbgTrace "Cannot Find GetSubItem object", 1
             Else
               DbgTrace "FOUND GetSubItem object", 1
               intNBInSelection = intNBInSelection + 1
               WriteToEXCEL intGReportCurrentRow, strGReportLabelBendStrIndexValue, _ 
                            objBendableString.InstanceName,0,0,0,0
               '//======================================
               '// Extract Tubing Data from the object
               '//======================================
               ExtractTubingData objBendableString
               objBendableString = Nothing
             End If       
         Next '//For intSubProdIndex =1 to intNumOfSubProducts
       End If
       Set objSysLineProduct = objCATIAV5Selection.FindObject("CATIAArrSystemLineProduct")
       if (Err.Number <> 0) Then 
          Set objSysLineProduct = Nothing
          Exit Do
       End If

       intGReportCurrentRow = intGReportCurrentRow +2
       InsertARowAt (intGReportCurrentRow)

    Loop  '// End Do ...each FindObject
  End If

  DbgTrace "total number of Product in selection = " & intNBInSelection, 0 
  If(intNBInSelection > 0) Then
    msgbox "Bendable String Extraction Complete"
  Else
    Dim strMsg          As String
    strMsg = "No bendable string objects found !!" + Chr(13)
    strMsg =  strMsg + "Please select a logical line or distribution system containing a bendable string on a Run."
    msgbox strMsg    
  End If

  ArrangeExcelColumns

  'EndEXCEL

End Sub '////////////////////////////////////////////////////////////// CATMain
