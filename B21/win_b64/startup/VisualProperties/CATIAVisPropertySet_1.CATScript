Language="VBSCRIPT"
'The goal of this macro is to demonstrate the change of visualization 
'properties of objects

Sub CATMain()
  Dim Selection0 As Selection
  Set Selection0 = CATIA.ActiveDocument.Selection

  Dim Obj2 As VisProperties
  Set Obj2 = Selection0.VisProperties

  'Changes the color of all objects to blue (RGB code=0,0,255) 
  'imposing inheritance
  Obj2.SetRealColor 0,0,255,1

  'Changes the transparency of all the objects to mid-transparency 
  ' (for opacity=128/255), and imposing inheritance
  Obj2.SetRealOpacity 128,1

End Sub
