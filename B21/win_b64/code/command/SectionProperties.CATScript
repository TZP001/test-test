'// COPYRIGHT DASSAULT SYSTEMES  1999
'//============================================================================
'//
'// Language="VBSCRIPT"
'// Sample of macro to extract the section properties for Structure Design
'//
'//============================================================================
'// This CATScript assumes that the user has selected Structural objects
'// from the CATIA Specification Viewer or the 3D Window.
'//
'// It is advised that the user understand the VBScript and VBA concepts before
'// attempting to modify the code to suit their needs. Microsoft Excel 97
'// provides excellent documentation on the use of VBScript and VBA.
'//============================================================================

dim excel as AnyObject
dim workbooks as AnyObject
dim workbook as AnyObject
dim sheets as AnyObject
dim sheet as AnyObject
dim excelTemplate as String
dim excelTemplatePath as String
dim strWB as Workbench
dim strServ as AnyObject
dim currentRow as integer

'//---------------------------------------------------------------------------
'// Default path of the excel file template 
'//---------------------------------------------------------------------------
strCATCommandPath = CATIA.SystemService.Environ("CATCommandPath")
excelTemplate = "SectionPropertiesTemplate.xls"
excelTemplatePath = InputBox("Path of the template:", _
                             "Input path for the EXCEL Template", _
                              strCATCommandPath + "\" + excelTemplate)

'//---------------------------------------------------------------------------
'// User customization of the attributes which will be extracted
'//---------------------------------------------------------------------------
dim nbColumns as integer
nbColumns = 8
dim column(8)
column(1) = "SectionName"
column(2) = "Area"
column(3) = "Ixx"
column(4) = "Iyy"
column(5) = "Vx"
column(6) = "Vy"
column(7) = "Rx"
column(8) = "Ry"


'//---------------------------------------------------------------------------
'// Start Excel
'//---------------------------------------------------------------------------
Sub StartEXCEL()
   Err.Clear
   On Error Resume Next
   Set excel = GetObject (,"EXCEL.Application")
   If Err.Number <> 0 Then
	   Err.Clear 
         Set excel = CreateObject ("EXCEL.Application") 
   End If 

   excel.Application.Visible = TRUE
   set workbooks = excel.Application.WorkBooks
   set workbook  = workbooks.Add(excelTemplatePath)
   If Err.Number <> 0 Then 
   	    Dim strMessage 
        strMessage  = "Error Loading Template File:" + excelTemplatePath + Chr(13) 
        strMessage  = strMessage + Chr(13) + "Check the following...." + Chr(13)
        strMessage  = strMessage + "(1)Template File has read-write capability" + Chr(13) 
        strMessage  = strMessage + "(2)Template File path is valid" 
        msgbox (strMessage)
        Err.Clear
   End If  
   set sheets = workbook.Worksheets
   set sheet = sheets("Parameters list")
   sheet.Select
End Sub 

'//---------------------------------------------------------------------------
'// Exit Excel
'//---------------------------------------------------------------------------
Sub EndEXCEL()
   workbook.Close
   excel.Quit
End Sub 

'//---------------------------------------------------------------------------
'// Write in Excel
'//---------------------------------------------------------------------------
Sub WriteInExcel(iRow, iColumn, iString)

   On Error Resume Next

   if (Len(iString) > 0) then
      dim whichColumn as integer
      whichColumn = 0

      Select Case iColumn
         Case "PartNumber"
	        whichColumn = 1
	     Case "Name"
	        whichColumn = 2
      End Select

      if (whichColumn = 0) then
         dim NotTheSame as Integer
         dim i as Integer
         NotTheSame = 0
       
	     for i = 1 to nbColumns
            NotTheSame = StrComp(column(i), iColumn, 0)
           
            if (NotTheSame = 0) then
  	            whichColumn = 2 + i
                Exit for
            end if
         Next 
      end if

      sheet.Cells(iRow, whichColumn) = iString
      sheet.Cells(iRow, whichColumn).Select
   end if
End Sub

'//---------------------------------------------------------------------------
'// Find parameters value
'//---------------------------------------------------------------------------
Sub PrintParameters(iProduct)
   dim parameters as Parameters
   dim param as Parameter
   dim nbParam as integer

   On Error Resume Next
   WriteInExcel currentRow, "PartNumber", iProduct.PartNumber
   WriteInExcel currentRow, "Name", iProduct.Name

   dim RefProduct as Product
   set RefProduct = iProduct.ReferenceProduct
   set parameters = iProduct.ReferenceProduct.Parameters

   nameProd = iProduct.Name
   
   Dim member as StrMember
   Dim members as StrMembers
   Dim section as StrSection
	
   Set members = iProduct.Parent.Parent.GetTechnologicalObject("StructureMembers")

   if (not(members is nothing)) then
		set member = members.Item(nameProd)
		set section = member.Section
	      if (section is nothing) then
        		strMessage  = "Section invalide" 
			msgbox (strMessage)
		end if
   end if

   nbParameters = parameters.Count
 
   dim i as Integer
   dim parm as Parameter
   dim cdgx, cdgy, cdgz as double

   if (not(section is nothing)) then
	  for i = 1 to nbColumns
            Err.Clear
	     if (column(i) = "Area") then
				dim area as double
				msgbox ("entree dans get property")
				section.GetProperty(CatStrArea) , area
                if (area > 0) then
    		    	WriteInExcel currentRow, column(i), area
                end if
	     Elseif (column(i) = "Ixx") then
				dim ixx as double
				section.GetProperty(CatStrInertiaXX) , ixx
                if (ixx > 0) then
    		    	WriteInExcel currentRow, column(i), ixx
                end if
	     Elseif (column(i) = "Iyy") then
				dim iyy as double
				section.GetProperty(CatStrInertiaYY) , iyy
                if (iyy > 0) then
    		    	WriteInExcel currentRow, column(i), iyy
                end if
	     Elseif (column(i) = "Vx") then
				dim vx as double
				section.GetProperty(CatStrModuleInertiaX) , vx
           		if (vx > 0) then
    	       		WriteInExcel currentRow, column(i), vx
           		end if
	     Elseif (column(i) = "Vy") then
				dim vy as double
				section.GetProperty(CatStrModuleInertiaY) , vy
           		if (area > 0) then
    	       		WriteInExcel currentRow, column(i), vy
           		end if
	     Elseif (column(i) = "Rx") then
				dim rx as double
				section.GetProperty(CatStrGirationModuleX) , rx
           		if (rx > 0) then
    	       		WriteInExcel currentRow, column(i), rx
           		end if
	     Elseif (column(i) = "Ry") then
				dim ry as double
				section.GetProperty(CatStrGirationModuleY) , ry
           		if (ry > 0) then
            		WriteInExcel currentRow, column(i), ry
           		end if
         Else
           		set param = parameters.GetItem(column(i))
            	if (Err.Number <> 0) Then Set param = Nothing
            	if (Not(param Is Nothing)) then
                		WriteInExcel currentRow, column(i), param.ValueasString
            	end if
         end if      
      Next
   end if
End Sub

'//---------------------------------------------------------------------------
'// Main
'//---------------------------------------------------------------------------
Sub CATMain()
   On Error Resume Next

   StartExcel

   dim product as Product
   dim nbProduct  as integer
   nbProduct = 0
   currentRow = 2

   dim doc as Document
   dim sel as Selection

   set doc = CATIA.ActiveDocument
   set strWB = doc.GetWorkbench("StrWorkbench")
   set strServ = strWB.StrComputeServices 

   set sel = doc.Selection
   set product = sel.FindObject("CATIAProduct")

   Do Until(product Is Nothing)
      nbProduct = nbProduct + 1
      PrintParameters(product)
      set product = sel.FindObject("CATIAProduct") 
      if (Err.Number <> 0)  then set product = Nothing
      currentRow = currentRow + 1
   Loop 

   ' EndExcel
End Sub
