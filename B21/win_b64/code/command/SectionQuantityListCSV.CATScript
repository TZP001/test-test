'// COPYRIGHT DASSAULT SYSTEMES  1999
'//============================================================================
'//
'// Language="VBSCRIPT"
'// Sample of macro to extract the Bill Of Material for Structure Design
'//
'//============================================================================
'// This CATScript assumes that the user has selected Structural objects
'// from the CATIA Specification Viewer or the 3D Window.
'//
'// It is advised that the user understand the VBScript and VBA concepts before
'// attempting to modify the code to suit their needs. Microsoft Excel 97
'// provides excellent documentation on the use of VBScript and VBA.
'//============================================================================

dim excel as AnyObject
dim workbooks as AnyObject
dim workbook as AnyObject
dim sheets as AnyObject
dim sheet as AnyObject
dim excelTemplate as String
dim excelTemplatePath as String
dim strWB as Workbench
dim strServ as AnyObject
dim currentRow as integer

'//---------------------------------------------------------------------------
'// User customization of the attributes which will be extracted
'//---------------------------------------------------------------------------

dim nbColumns as integer
nbColumns = 15
dim column(15)
column(1)  = "MemberType"
column(2)  = "SectionName"
column(3)  = "FamilyName"
column(4)  = "CatalogName"
column(5)  = "Length"
column(6)  = "PlateType"
column(7)  = "Thickness"
column(8)  = "Surface"
column(9)  = "Wet area"
column(10) = "Volume"
column(11) = "Material"
column(12) = "Mass"
column(13) = "CdgX"
column(14) = "CdgY"
column(15) = "CdgZ"

'//---------------------------------------------------------------------------
'// Find parameters value
'//---------------------------------------------------------------------------

Sub PrintParameters(iText as TextStream, iProduct as Product)
   
   dim parameters as Parameters
   dim userParameters as Parameters
   dim param as Parameter
   dim nbParam as integer
   dim textLine as string

   On Error Resume Next
   textLine = Cstr(iProduct.PartNumber) & ";"
   textLine = textLine & Cstr(iProduct.Name) & ";"

   dim RefProduct as Product
   set RefProduct = iProduct.ReferenceProduct
   set parameters = iProduct.ReferenceProduct.Parameters
   set userParameters = iProduct.ReferenceProduct.UserRefProperties

   Dim plate As StrPlate
   nameProd = iProduct.Name
   
   Dim plates as StrPlates
	
   Set plates = iProduct.Parent.Parent.GetTechnologicalObject("StructurePlates")

   if (not(plates is nothing)) then
	set plate = plates.Item(nameProd)
   end if

   nbParameters = parameters.Count

   dim i as Integer
   dim parm as Parameter
   dim cdgx, cdgy, cdgz as double

   if (nbParameters > 0) then

	  for i = 1 to nbColumns
         	Err.Clear
	     
		 ' length to cut for a member
		 if (column(i) = "Length") then
		    	dim length as double
		    	length = strWB.StrComputeServices.GetLength(iProduct)
            
			    if (length > 0) then
               		textLine = textLine & Cstr(length) 
            	end if
	     
		 ' thickness for a plate
		 Elseif (column(i) = "Thickness") then
		    	dim thickness as double
		    
			    if (Not(plate Is Nothing)) then
               		thickness = plate.StandardThickness
               		textLine = textLine & Cstr(thickness) 
            	end if

	     ' surface for a plate 
	     Elseif (column(i) = "Surface") then
		    	dim surface as double
		    	surface = strWB.StrComputeServices.GetSurface(iProduct)
            
			    if (surface > 0) then
		      	    textLine = textLine & Cstr(surface) 
            	end if

         ' wet area for structure objects
	     Elseif (column(i) = "Wet area") then
		    	dim wetarea as double
		    	wetarea = strWB.StrComputeServices.GetWetArea(iProduct)

            	if (wetarea > 0) then
				    textLine = textLine & Cstr(wetarea) 
            	end if

         ' volume for structure object
	     Elseif (column(i) = "Volume") then
		    	dim volume as double
		    	volume = strWB.StrComputeServices.GetVolume(iProduct)
                    
			    if (volume > 0) then
		      	    textLine = textLine & Cstr(volume)
            	end if

	     ' mass for structure object
	     Elseif (column(i) = "Mass") then
		    	dim mass as double
            	mass = strWB.StrComputeServices.GetMass(iProduct)
            
			    if (mass > 0) then
    		   		textLine = textLine & Cstr(mass) 
            	end if

         ' material
		 Elseif (column(i) = "Material") then
		        dim mat as string
                mat = strWB.StrComputeServices.GetMaterialName(iProduct)
             	textLine = textLine & mat 
         Elseif (column(i) = "CdgX") then
		    	strWB.StrComputeServices.GetCenterOfGravity(iProduct),cdgx,cdgy,cdgz
			    textLine = textLine & Cstr(cdgx) 
         Elseif (column(i) = "CdgY") then
		    	strWB.StrComputeServices.GetCenterOfGravity(iProduct),cdgx,cdgy,cdgz
			    textLine = textLine & Cstr(cdgy) 
	     Elseif (column(i) = "CdgZ") then
		    	strWB.StrComputeServices.GetCenterOfGravity(iProduct),cdgx,cdgy,cdgz
			    textLine = textLine & Cstr(cdgz)          
		 ' user attribute
		 Else
            	set param = parameters.Item(column(i))
            	if (Err.Number <> 0) Then Set param = Nothing
	        
			    ' f(x) attribute
			    if (Not(param Is Nothing)) then
               		textLine = textLine & Cstr(param.ValueAsString) 

		    	' user propertie on product
            	else
				    Err.Clean
			   	    set param = userParameters.Item(column(i))
               
	           	    if (Not(param Is Nothing)) then
                  		textLine = textLine & Cstr(param.ValueAsString) 
               	    end if
		        end if
         end if   
		 
		 textLine = textLine & ";"   
      Next
   end if

   ' write the line
   iText.Write(textLine)
   iText.Write(Chr(10))

End Sub

'//---------------------------------------------------------------------------
'// Main
'//---------------------------------------------------------------------------

Sub CATMain()
   
   On Error Resume Next

   dim fileSystem as FileSystem
   set fileSystem = CATIA.FileSystem

   dim bomFile as File
   set bomFile = fileSystem.CreateFile("e:\tmp\bom.txt", true) 

   dim text as TextStream
   set text = bomFile.OpenAsTextStream("ForWriting")	

   dim product as Product
   dim nbProduct  as integer
   nbProduct = 0

   dim doc as Document
   dim sel as Selection

   set doc = CATIA.ActiveDocument
   set strWB = doc.GetWorkbench("StrWorkbench")
   set strServ = strWB.StrComputeServices 

   set sel = doc.Selection

   dim str as string
   str = sel.SelectElement2("Product","Select objects", true)
   
   Dim number 
   number = sel.Count
   msgbox "Total number of selected objects "&Cstr(number)
   
   dim selectEl as SelectedElement
   
   for i=1 to number
   
      set selectEl = sel.Item(i)
      
      set product = selectEl.Value
      'msgbox "Product name = " &product.Name
      nbProduct = nbProduct + 1
       PrintParameters text, product
       
       Err.clean
   next

   text.Close
End Sub
