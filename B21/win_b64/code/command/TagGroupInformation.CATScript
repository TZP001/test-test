'// ---------- CATIAV5 application objects
'====================================================================================
Sub CATMain ()
'====================================================================================

  Dim objCATIAV5TagGroup As TagGroup
  Dim objCATIAV5Tag As Tag
  Dim Name As String
  Dim FrmType As String

  Set Parentobject = CATIA.ActiveDocument.Selection.FindObject("CATIAProduct")	
  Set objCATIAV5TagGroup = Parentobject.GetTechnologicalObject("TagGroup")
  objCATIAV5TagGroup.CreateTag objCATIAV5Tag
  msgbox("Created Tag name is")
  objCATIAV5Tag.GetName Name
  msgbox(Name)

  Dim List(100)
  objCATIAV5TagGroup.GetTagList List 
  msgbox("Existing List of Tags")

  Dim count As Integer
  count = objCATIAV5TagGroup.Count
  For i = 0 To count-1
  	msgbox(List(i))
  Next

  msgbox("Names and Frame types of Tags are")
  For i = 1 To objCATIAV5TagGroup.Count
  	Set Tag = objCATIAV5TagGroup.GetTag(i)
    Tag.GetName Name
    msgbox(Name)
    Tag.GetType FrmType
  	msgbox(FrmType)  
  Next

End Sub '/////////////////////////////////////////////////////////// CATMain
