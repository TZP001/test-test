'// COPYRIGHT DASSAULT SYSTEMES  1999
'//============================================================================
'//
'// Language="VBSCRIPT"
'// To extract the "footprint" of objects in CSO. We use the word "footprint"
'// to indicated the projected area of an object onto the x-y plane.
'//
'//============================================================================
'// Major CATIA interface used:
'//
'// interface                  VB Name          Remarks
'// -----------               ------------      --------------
'// CATIADocument             Document          access the current document
'// CATIAWorkbench            workbench         access the Manufacturing Systems 
'//                                             Layout workbench, 
'//                                             calculate footprint,
'//                                             get the current user units ...
'// CATIASelection            Selection         to get the object from CSO in the 
'//                                             interactive section
'// CATIAProduct              Product           to get the Product Ids ... 
'// CATIAArrNomenclatures     ArrNomenclatures  to filter out objects based
'//                                             on user nomenclature
'// CATIAArrNomenclature      ArrNomenclature   get system type name
'//                                             given a user defined nomenclature
'//
'//============================================================================
'//
'// Audit Trail:
'//----------------------------------------------------------------------------
'//   Author     : Vic Szeto
'//   Date       : 8/99
'//   Chg id     :
'//   Chg nature :
'//----------------------------------------------------------------------------
'//   Modified   :
'//   Date       :
'//   Chg id     :
'//   Chg nature :
'//============================================================================

Option Explicit

'******************************************************************************
'  GLOBAL variable declarations section
'******************************************************************************
'// ---------- Debug Traces
Const intG_TRACEON = 1
Dim strMessage

'//--------- global calculation variables
Dim dbGAreaUsedSize As double
Dim dbGAreaTotalSize As double
Dim dbGAreaFreeSize As double
Dim dbGAreaFreePercent As double
Dim dbGAreaUsedPercent As double

'//---------- EXCEL application 
Dim objGEXCELapp As Object
Dim objGEXCELwkBks As Object
Dim objGEXCELwkBk As Object
Dim objGEXCELwkShs As Object
Dim objGEXCELSh As Object

'// ---------- CATIAV5 application objects
Dim objCATIAV5Document0 As Document
Dim objCATIAV5ArrWorkbench0 As Workbench
Dim objCATIAV5Selection As Selection

Dim intGReportCurrentRow

'@@@@@@@@@@@@@@@@@@@@@@@@@@@@@@@@@@@@@@@@@@@@@@@@@@@@@@@@@@@@@@@@@@@@@@@@@@@@@@
'//                       User customizable sections                  
'@@@@@@@@@@@@@@@@@@@@@@@@@@@@@@@@@@@@@@@@@@@@@@@@@@@@@@@@@@@@@@@@@@@@@@@@@@@@@@

'//---------- EXCEL report format
Const strGReportLabAreaUnit = "Area Units"
Const intGReportAreaUnitCol = 1
Const intGReportAreaUnitRow = 11

Const strGReportLabSelArea = "Selected Area"
Const intGReportSelAreaCol = 1
Const intGReportSelAreaRow = 12

Const strGReportLabelAreaTotalSize = "Total Area Size"
Const intGReportAreaTotalSizeCol = 2
Const intGReportAreaTotalSizeRow = 14

Const strGReportLabelAreaUsedSize = "Used Area Size"
Const intGReportAreaUsedSizeCol = 2
Const intGReportAreaUsedSizeRow = 15

Const strGReportLabelAreaFreeSize = "Free Area Size"
Const intGReportAreaFreeSizeCol = 2
Const intGReportAreaFreeSizeRow = 16

'//---------- this data affects the chart in EXCEL
Const strGReportLabelAreaFreePercent = "Free Area Percentage"
Const intGReportAreaFreePercentCol = 4
Const intGReportAreaFreePercentRow = 16

'//---------- this data affects the chart in EXCEL
Const strGReportLabelAreaUsedPercent = "Used Area Percentage"
Const intGReportAreaUsedPercentCol = 4
Const intGReportAreaUsedPercentRow = 15

Const strGReportLabelAreaName = "Area Name"
Const intGReportAreaNameCol = 1
Const strGReportLabelAreaSize = "Area Size"
Const intGReportAreaSizeCol = 2

Const intGReportStartAfterRow = 26
Const intGReportStartAfterCol = 0

'========== EXCEL template direction path
Const strGReportTemplate = "d:\DSABestSoFar\intel_a\code\command\PslFootprintTemplate.xls" 

'---------- must name the sheet in the template accordingly
Const strGReportEXCELSheetName = "Area Distribution"

'@@@@@@@@@@@@@@@@@@@@@@@@@@@@@@@@@@@@@@@@@@@@@@@@@@@@@@@@@@@@@@@@@@@@@@@@@@@@@@

'------------------------------------------------------------------------------
Sub DbgTrace (iStrMsgString, iIntYesError)
'------------------------------------------------------------------------------
If (intG_TRACEON = 1) Then
  CATIA.SystemService.Print iStrMsgString 
  If (iIntYesError = 1) Then 
	   CATIA.SystemService.Print "Err Number = " & Err.Number
	End If
End If

End Sub '///////////////////////////////////////////////////////////// DbgTrace

'------------------------------------------------------------------------------
Sub StartEXCEL()
'------------------------------------------------------------------------------

  Err.Clear
  On Error Resume Next
  Set objGEXCELapp = GetObject (,"EXCEL.Application")  
  If Err.Number <> 0 Then   
     Err.Clear
     Set objGEXCELapp = CreateObject ("EXCEL.Application")
  End If

  objGEXCELapp.Application.Visible = TRUE
  Set objGEXCELwkBks = objGEXCELapp.Application.WorkBooks
  Set objGEXCELwkBk = objGEXCELwkBks.Add (strGReportTemplate)

  If Err.Number <> 0 Then
     Dim strMessage
     strMessage  = "Error Loading Template File:" + strGReportTemplate + Chr(13)
     strMessage  = strMessage + Chr(13) + "Check the following...." + Chr(13)
     strMessage  = strMessage + "(1)Template File has read-write capability" + Chr(13)
     strMessage  = strMessage + "(2)Template File path is valid"
	   msgbox (strMessage)
     Err.Clear
  End If

  Set objGEXCELwkShs = objGEXCELwkBk.Worksheets
  Set objGEXCELSh = objGEXCELwkBk.Sheets (strGReportEXCELSheetName)

End Sub '/////////////////////////////////////////////////////////// StartEXCEL

'------------------------------------------------------------------------------
Sub EndEXCEL ()
'------------------------------------------------------------------------------
  objGEXCELwkBk.Close
  objGEXCELapp.Quit
End Sub '///////////////////////////////////////////////////////////// EndEXCEL

'------------------------------------------------------------------------------
Sub StartCATIAV5 ()
'------------------------------------------------------------------------------
  Set objCATIAV5Document0 = CATIA.ActiveDocument
  DbgTrace "V5: Active Document",1

  '//---------- Get Arrworkbench from current document
  Set objCATIAV5ArrWorkbench0 = objCATIAV5Document0.GetWorkbench("ArrWorkbench") 
  DbgTrace "V5: GetWorkbench0",1

  '//---------- Get current selection
  Set objCATIAV5Selection = objCATIAV5Document0.Selection
  DbgTrace "V5: Selection",1

End Sub '///////////////////////////////////////////////////////// StartCATIAV5

'------------------------------------------------------------------------------
Sub WriteToEXCEL (iRow, iLabel, iString)
'------------------------------------------------------------------------------
  Dim WhichColumn
  WhichColumn = 0
  Select Case iLabel
      Case strGReportLabAreaUnit
         WhichColumn = intGReportAreaUnitCol
      Case strGReportLabSelArea
         WhichColumn = intGReportSelAreaCol
      Case strGReportLabelAreaTotalSize
         WhichColumn = intGReportAreaTotalSizeCol
      Case strGReportLabelAreaUsedSize
         WhichColumn = intGReportAreaUsedSizeCol
      Case strGReportLabelAreaFreeSize
         WhichColumn = intGReportAreaFreeSizeCol 
      Case strGReportLabelAreaFreePercent
         WhichColumn = intGReportAreaFreePercentCol
      Case strGReportLabelAreaUsedPercent
         WhichColumn = intGReportAreaUsedPercentCol
      Case strGReportLabelAreaName
         WhichColumn = intGReportAreaNameCol
      Case strGReportLabelAreaSize
         WhichColumn = intGReportAreaSizeCol
  End Select

  If (WhichColumn > 0) Then
     objGEXCELSh.Cells (iRow,WhichColumn) = iString
  End If

End Sub '///////////////////////////////////////////////////////// WriteToEXCEL

'------------------------------------------------------------------------------
Sub DoOneArea(iobjCATIAV5Area)
'------------------------------------------------------------------------------

  Dim intK
	Dim intUnsupportedType  As integer
  Dim objArea      As Product
  Dim objProducts  As Products
  Dim dbAreaSize   As double
  Dim intAreaCount As integer
  Dim strAreaName
	Dim strIntSysName 
	Dim strNomen
	Dim objNomenTree As ArrNomenclatureTree
	Dim objNomen     As ArrNomenclature
  
  On Error Resume Next

	Set objNomenTree = objCATIAV5ArrWorkbench0.ArrNomenclatureTree

  DbgTrace "Name = " & iobjCATIAV5Area.Name, 0
  WriteToEXCEL intGReportSelAreaRow,strGReportLabSelArea,iobjCATIAV5Area.Name 
	dbGAreaTotalSize = objCATIAV5ArrWorkbench0.CalculateFootprint(iobjCATIAV5Area)              

  Set objProducts = iobjCATIAV5Area.Products
  intAreaCount = objProducts.Count
  DbgTrace "number of areas = " & intAreaCount,0

  For intK = 1 to intAreaCount

	  dbAreaSize = 0.0

	  DbgTrace "------- intK = " & intK,0
	  intUnsupportedType = 0
    Set objArea = objProducts.Item(intK)

		'---------- Get Product Name
    strAreaName = objArea.Name

    '---------- Get Product Nomenclature Type		
		strNomen = objArea.Nomenclature

		'---------- Get MSL object internal system name based on PRODUCT nomenclature
		strIntSysName = ""
		If (Len (strNomen) > 0) Then
		   DbgTrace "strNomen = " & strNomen, 0
       Set objNomen = objNomenTree.GetNomenclature (strNomen)
			 strIntSysName = objNomen.IntSysClassName
			 DbgTrace "system name = " & strIntSysName, 0
		End If

    '---------- Screen out the unsupported types
    '---------- ArrRun and ArrPathWay are calculated
    '---------- only when they are under a Network system
    If ( (StrComp (strIntSysName, "ArrRun") = 0 )             Or _
		     (StrComp (strIntSysName, "ArrPathWay") = 0 )         Or _
				 (StrComp (strIntSysName, "ArrGrid") = 0)             Or _
				 (StrComp (strIntSysName, "ArrParallelXGrid") = 0)    Or _
				 (StrComp (strIntSysName, "ArrParallelYGrid") = 0)    Or _
  			 (StrComp (strIntSysName, "ArrParallelZGrid") = 0)    Or _
         (StrComp (strIntSysName, "ArrGridPlane") = 0)        Or _
         (StrComp (strIntSysName, "RoutableRectangle") = 0)   Or _
  			 (StrComp (strIntSysName, "RoutableLinesLoop") = 0)   ) Then
		   intUnsupportedType = 1
		End If

		'---------- Get Area Size
		If (intUnsupportedType = 0) Then
       dbAreaSize = objCATIAV5ArrWorkbench0.CalculateFootprint(objArea)
		   DbgTrace "Area size = " & dbAreaSize,0
		End If

    If ((Len (strAreaName) > 0) And (intUnsupportedType = 0)) Then
       WriteToEXCEL intGReportCurrentRow, strGReportLabelAreaName, strAreaName
       WriteToEXCEL intGReportCurrentRow, strGReportLabelAreaSize, dbAreaSize
       dbGAreaUsedSize = dbGAreaUsedSize + dbAreaSize
       intGReportCurrentRow = intGReportCurrentRow + 1
    End If

  Next  'For intK

  '---------- Do area analysis 
  dbGAreaFreeSize = dbGAreaTotalSize - dbGAreaUsedSize
	DbgTrace "dbGAreaFreeSize = " & dbGAreaFreeSize,0
	DbgTrace "dbGAreaUsedSize = " & dbGAreaUsedSize,0
	DbgTrace "dbGAreaTotalSize = " & dbGAreaTotalSize,0

  WriteToEXCEL intGReportAreaTotalSizeRow, _
                  strGReportLabelAreaTotalSize, dbGAreaTotalSize 
  WriteToEXCEL intGReportAreaFreeSizeRow, _
                  strGReportLabelAreaFreeSize, dbGAreaFreeSize   
  WriteToEXCEL intGReportAreaUsedSizeRow, _
                  strGReportLabelAreaUsedSize, dbGAreaUsedSize 

  dbGAreaFreePercent = (dbGAreaFreeSize/dbGAreaTotalSize)
  WriteToEXCEL intGReportAreaFreePercentRow, _
               strGReportLabelAreaFreePercent, dbGAreaFreePercent 
  dbGAreaUsedPercent = 1.0 - dbGAreaFreePercent
  WriteToEXCEL intGReportAreaUsedPercentRow, _
               strGReportLabelAreaUsedPercent, dbGAreaUsedPercent 

End Sub '//////////////////////////////////////////////////////////// DoOneArea

'------------------------------------------------------------------------------
Sub CATMain()
'------------------------------------------------------------------------------

  StartEXCEL

  StartCATIAV5

  dbGAreaUsedSize  = 0.0
  dbGAreaFreeSize  = 0.0
  dbGAreaTotalSize = 0.0
  
  Dim objArea As Area  
  Dim intNBInSelection  As integer
	Dim strAreaUnit

  intNBInSelection = 0
  On Error Resume Next

	strAreaUnit = objCATIAV5ArrWorkbench0.GetCurrentUnits("AREA")
	strAreaUnit = "Area Units: " & strAreaUnit
  WriteToEXCEL intGReportAreaUnitRow, _
               strGReportLabAreaUnit, strAreaUnit 
  
  Set objArea = objCATIAV5Selection.FindObject("CATIAProduct")
  DbgTrace "FindObject", 1
  if (Err.Number <> 0) Then Set objArea = Nothing

  intGReportCurrentRow = intGReportStartAfterRow + 1
  Do Until ( objArea Is Nothing )

     intNBInSelection = intNBInSelection + 1
     DoOneArea objArea

     Set objArea = objCATIAV5Selection.FindObject("CATIAProduct")
     if (Err.Number <> 0) Then Set objArea = Nothing

  Loop  '// End Do ...each FindObject
  
  DbgTrace "total number of Product in selection = " & intNBInSelection, 0 

End Sub '////////////////////////////////////////////////////////////// CATMain
