'********************************************************************
'********************************************************************
'****  VBSCRIPT MACRO FOR THE GENERATION OF HTML DOCUMENTATION   ****
'****              Steve Morissette 04/01/99                     ****
'********************************************************************
'********************************************************************

Language="VBSCRIPT"

Dim OutRef, OutPath, OutIndex

Sub CATMain()
  MsgBox("This macro cannot be run directly !")
End Sub

'--------------------------------------------------------------------
' Main Procedure
'--------------------------------------------------------------------
Sub CATDocument( RootActivityName, HtmlFilesName, HtmlFilesPath)
CATIA.SystemService.Print "RootActivityName : " & RootActivityName
CATIA.SystemService.Print "HtmlFilesName : " & HtmlFilesName
CATIA.SystemService.Print "HtmlFilesPath : " & HtmlFilesPath
  Dim RootActivity
  Dim RootActName
  RootActName = RootActivityName
  OutPath = HtmlFilesPath
  OutRef = HtmlFilesName
  OutIndex = OutRef & "_index.html"
  Set RootActivity = Catia.ActiveDocument.GetItem(RootActName)
  CreateIndex RootActivity, OutPath, OutRef, OutIndex
End Sub


'---------------------------------------------------------------
' Create the index file
'---------------------------------------------------------------'
Sub CreateIndex(RootActivity, OutPath, OutRef, OutIndex)
  Dim indexfs
  Dim indexf

  Set indexfs = CreateObject("Scripting.FileSystemObject")
  Set indexf = Indexfs.OpenTextFile(OutPath & OutIndex, 2, True)

  'Write index file header
  indexf.WriteLine "<!doctype html public ""-//w3c//dtd html 4.0 transitional//en"">"
  indexf.WriteLine "<html>"
  indexf.WriteLine "<head>"
  indexf.WriteLine "   <meta http-equiv=""Content-Type"" content=""text/html; charset=iso-8859-1"">"
  indexf.WriteLine "   <meta name=""GENERATOR"" content=""IPD v2"">"
  indexf.WriteLine "   <meta name=""Author"" content=""IPD v2"">"
  indexf.WriteLine "   <title>Activities Index for Process : " & RootActivity.Name & "</title>"
  indexf.WriteLine "</head>"
  indexf.WriteLine "<body background=""back.gif"" bgcolor=#EEEEFF>"

  indexf.WriteLine "<CENTER>"
  indexf.WriteLine "<P><h2>Activities Index for Process : <I>" & RootActivity.Name & "</I></h2>"
  indexf.WriteLine "<I>Generation Date : " & Date & " at " & Time & "</I></P>"

  indexf.WriteLine "</CENTER>"
  indexf.WriteLine "<P><TABLE BORDER COLS=1 WIDTH=""100%"" >"
  indexf.WriteLine "<TR ALIGN=CENTER BGCOLOR=#CCCCCC><TD><B>Activities Hierarchy</B></TD></TR></TABLE>"
  indexf.WriteLine "<TABLE BORDER COLS=5 WIDTH=""100%"" >"
  indexf.WriteLine "<TR ALIGN=CENTER BGCOLOR=#EEEEEE>"
  indexf.WriteLine "<TD WIDTH=""30%""><B>Name</B></TD>"
  indexf.WriteLine "<TD WIDTH=""40%""><B>Description</B></TD>"
  indexf.WriteLine "<TD WIDTH=""10%""><B>Cycle Time</B></TD>"
  indexf.WriteLine "<TD WIDTH=""10%""><B>Begin Date</B></TD>"
  'indexf.WriteLine "<TD WIDTH=""10%""><B>End Date</B></TD>"
  indexf.WriteLine "</TR>"

  'Write reference
  WriteIndexRef RootActivity, indexf, OutPath, OutRef, 0
  indexf.WriteLine "</TD></TR></TABLE></P>"

  'Generate the index image file
  If (RootActivity.Parent.Name = CATIA.ActiveDocument.Name) Then
    indexf.WriteLine "<P><TABLE BORDER COLS=1 WIDTH=""100%"" >"
    indexf.WriteLine "<TR ALIGN=CENTER BGCOLOR=#CCCCCC><TD><B>Activities Sequence</B>"
    indexf.WriteLine "</TD></TR></TABLE>"
    CATIA.ActiveWindow.ActiveViewer.Reframe
    name=OutPath & OutRef & ".jpg"
    CATIA.ActiveWindow.ActiveViewer.CaptureToFile 5, name
    indexf.WriteLine "<P><CENTER><IMG SRC=""file:/" & name & """</CENTER></P>"
  End If

  'Write index file footer

End Sub

'---------------------------------------------------------------
' Write the index reference for an activity
'---------------------------------------------------------------
Function WriteIndexRef(Activity, File, OutPath, OutRef, Level)
  Dim childs
  Dim child
  Dim quantity
  Dim I

   If (Activity.IsSubTypeOf("PhysicalActivity")) Then

    'Write reference for the activity itself
    File.WriteLine "<TR VALIGN=TOP BGCOLOR=#FFFFFF><TD><A HREF = """ & OutRef & "_" & Activity.Name & ".html"">"
	'Indent the name according to the level of the activity
	Dim J
	For J = 0 To Level
	  File.Write "--"
	Next
	File.WriteLine Activity.Name & "</A></TD>"
	File.WriteLine "<TD>" & Activity.Description & "</TD>"
	File.WriteLine "<TD>" & Activity.CycleTime & "</TD>"
	File.WriteLine "<TD>" & Activity.BeginningDate & "</TD>"
On Error Resume Next
    File.WriteLine "<TD>" & Activity.EndDate & "</TD></TR>"
    'Write the activity detail file
    WriteActivityFile Activity, OutPath, OutRef

    'Write the list
    Set childs = Activity.ChildrenActivities
    quantity = childs.Count

    if quantity <= 0 then
      Exit Function
    End if
    'Recursively write sons
    For I=1 To quantity
      Set child = childs.Item(I)
      WriteIndexRef child,File,OutPath,OutRef,Level+1
    Next
  End if

End Function

'---------------------------------------------------------------
' Write the activity file
'---------------------------------------------------------------
Sub WriteActivityFile(Activity, OutPath, OutRef)
  Dim fs
  Dim file
  Set fs = CreateObject("Scripting.FileSystemObject")
  Set file = fs.OpenTextFile(OutPath & OutRef & "_" & Activity.Name & ".html", 2, True)
  WriteHeader Activity, file
  WriteCore Activity, file
  WriteFooter Activity, file
End Sub

'---------------------------------------------------------------
' Write an activity file header
'---------------------------------------------------------------
Sub WriteHeader(Activity, File)
  File.WriteLine "<!doctype html public ""-//w3c//dtd html 4.0 transitional//en"">"
  File.WriteLine "<html>"
  File.WriteLine "<head>"
  File.WriteLine "   <meta http-equiv=""Content-Type"" content=""text/html; charset=iso-8859-1"">"
  File.WriteLine "   <meta name=""GENERATOR"" content=""IPD v2"">"
  File.WriteLine "   <meta name=""Author"" content=""IPD v2"">"
  File.WriteLine "   <title>Activity Detail : " & Activity.Name & "</title>"
  File.WriteLine "</head>"
  File.WriteLine "<body background=""back.gif"" bgcolor=#EEEEFF>"

  File.WriteLine "<CENTER>"
  File.WriteLine "<P><h2>Activity Detail : <I>" & Activity.Name & "</I></h2>"
  File.WriteLine "<I>Generation Date : " & Date & " at " & Time & "</I></P>"

  File.WriteLine "</CENTER>"
End Sub

'---------------------------------------------------------------
' Write an activity file core
'---------------------------------------------------------------
Sub WriteCore(Activity, File)
  File.WriteLine "<P><TABLE BORDER COLS=2 WIDTH=""100%"" >"
  File.WriteLine "<TR ALIGN=CENTER BGCOLOR=#CCCCCC><TD><B>General Data</B></TD><TD><B>Specific Data</B></TD></TR>"
  File.WriteLine "<TR VALIGN=TOP BGCOLOR=#FFFFFF>"
  File.WriteLine "<TD><B>Name : </B>" & Activity.Name & "<BR>"
  File.WriteLine "<B>Type : </B>" & Activity.Type & "<BR>"
  File.WriteLine "<B>Description : </B>" & Activity.Description & "<BR>"
  File.WriteLine "<B>Cycle Time : </B>" & Activity.CycleTime & "<BR>"
  File.WriteLine "<B>Calculated Cycle Time : </B>" & Activity.CalculatedCycleTime & "<BR>"
  File.WriteLine "<B>Begin Date : </B>" & Activity.BeginningDate & "<BR>"
On Error Resume Next
  File.WriteLine "<B>End Date : </B>" & Activity.EndDate & "<BR></TD>"
  'SUB for specific data
  File.WriteLine "<TD>"
  WriteSpecific Activity, File
  File.WriteLine "</TD>"
  File.WriteLine "</TR>"
  File.WriteLine "</TABLE></P>"

  File.WriteLine "<P><TABLE BORDER COLS=2 WIDTH=""100%"" >"
  File.WriteLine "<TR ALIGN=CENTER BGCOLOR=#CCCCCC><TD><B>Items List</B></TD><TD><B>Resources List</B></TD></TR>"
  'SUB for items list
  File.WriteLine "<TR VALIGN=TOP BGCOLOR=#FFFFFF><TD>"
  WriteItems Activity, File
  File.WriteLine "</TD>"
  'SUB for resources list
  File.WriteLine "<TD>"
  WriteResources Activity, File
  File.WriteLine "</TD>"
  File.WriteLine "</TR>"
  File.WriteLine "</TABLE></P>"
End Sub

'---------------------------------------------------------------
' Write an activity item list
'---------------------------------------------------------------
Sub WriteItems(Activity, File)
  Dim items,item,quantity
  Set items = Activity.Items
  quantity = items.Count
  if quantity <= 0 then
    File.WriteLine "None"
    exit sub
  end if
  File.WriteLine "<UL>"
  For I=1 To quantity
    Set item = items.Item(I)
	File.WriteLine "<LI>" & item.Name & "</LI>"
  Next
  File.WriteLine "</UL>"
End Sub

'---------------------------------------------------------------
' Write an activity resource list
'---------------------------------------------------------------
Sub WriteResources(Activity, File)
  Dim items,item,quantity
  Set items = Activity.Resources
  quantity = items.Count
  if quantity <= 0 then
    File.WriteLine "None"
    exit sub
  end if
  File.WriteLine "<UL>"
  For I=1 To quantity
    Set item = items.Item(I)
	File.WriteLine "<LI>" & item.Name & "</LI>"
  Next
  File.WriteLine "</UL>"
End Sub

'---------------------------------------------------------------
' Write an activity file footer
'---------------------------------------------------------------
Sub WriteFooter(Activity, File)
  File.WriteLine "<P><TABLE BORDER COLS=1 WIDTH=""100%"" >"
  File.WriteLine "<TR ALIGN=CENTER BGCOLOR=#CCCCCC><TD><B>Related Activities</B></TD></TR></TABLE>"

  File.WriteLine "<TABLE BORDER COLS=4 WIDTH=""100%"" >"
  File.WriteLine "<TR VALIGN=TOP BGCOLOR=#FFFFFF>"
  File.WriteLine "<TD><B><<<< Previous</B>"
  WritePrevious Activity, File
  File.WriteLine "</TD>"

  File.WriteLine "<TD><B>Parent</B>"
  'File.WriteLine "<BR><A HREF = """ & "bidon.html" & """>" & "parent_name" & "</A></TD>"
  File.WriteLine "</TD>"

  File.WriteLine "<TD><B>Childs</B>"
  WriteChilds Activity, File
  File.WriteLine "</TD>"

  File.WriteLine "<TD><B>Next >>>></B>"
  WriteNext Activity, File
  File.WriteLine "</TD>"

  File.WriteLine "</TR>"
  File.WriteLine "</TABLE></P>"

  File.WriteLine "<P><B><I><A HREF = """ & OutIndex & """>Activities Index</I></B>"

End Sub

'---------------------------------------------------------------
' Write the previous list
'---------------------------------------------------------------
Sub WritePrevious(Activity, File)
  Dim activities
  Dim one
  Dim quantity
  Dim I

  Set activities = Activity.PreviousCFActivities
  quantity = activities.Count
  if quantity <= 0 then
    exit sub
  end if
   File.WriteLine "<UL>"
  for I = 1 to quantity
    Set one = activities.Item(I)
    If (one.IsSubTypeOf("PhysicalActivity")) Then
      File.WriteLine "<LI><A HREF = """ & OutRef & "_" & one.Name & ".html" & """>" & one.Name & "</A></LI>"
	End If
	If one.Type = "AndIn" Or one.Type = "OrIn" Or one.Type = "Switch" Or one.Type = "AndOut" then
	  File.WriteLine "<LI><I><B>" & one.Type & "</B></I></LI>"
	  WritePrevious one, File
	End If
  next
  File.WriteLine "</UL>"
End Sub

'---------------------------------------------------------------
' Write the Childs list
'---------------------------------------------------------------
Sub WriteChilds(Activity, File)
  Dim activities
  Dim one
  Dim quantity
  Dim I

  Set activities = Activity.ChildrenActivities
  quantity = activities.Count
  if quantity <= 0 then
    exit sub
  end if

  File.WriteLine "<UL>"
  for I = 1 to quantity
    Set one = activities.Item(I)
    If (one.IsSubTypeOf("PhysicalActivity")) Then
	  File.WriteLine "<LI><A HREF = """ & OutRef & "_" & one.Name & ".html" & """>" & one.Name & "</A></LI>"
	End If
  next
  File.WriteLine "</UL>"
End Sub

'---------------------------------------------------------------
' Write the next list
'---------------------------------------------------------------
Sub WriteNext(Activity, File)
  Dim activities
  Dim one
  Dim quantity
  Dim I

  Set activities = Activity.NextCFActivities
  quantity = activities.Count
  if quantity <= 0 then
    exit sub
  end if

  File.WriteLine "<UL>"
  for I = 1 to quantity
    Set one = activities.Item(I)
    If (one.IsSubTypeOf("PhysicalActivity")) Then
	  File.WriteLine "<LI><A HREF = """ & OutRef & "_" & one.Name & ".html" & """>" & one.Name & "</A></LI>"
	End If
	If one.Type = "AndOut" Or one.Type = "Switch" Or one.Type = "AndIn" Or one.Type = "OrIn" then
	  File.WriteLine "<LI><I><B>" & one.Type & "</B></I></LI>"
	  WriteNext one, File
	End If
  next
  File.WriteLine "</UL>"
End Sub

'---------------------------------------------------------------
' Write an activity file specific data block
'---------------------------------------------------------------
Sub WriteSpecific(Activity, File)
  If (Activity.IsSubTypeOf("PhysicalActivity")) Then
    Nbr=Activity.AttrCount
    If (Nbr > 0) Then
      For I=1 To Nbr
        name = Activity.AttrName(I)
        File.WriteLine "<B>" & name & " : </B>"
        AttrVal = Activity.AttrValue(I)
        File.WriteLine AttrVal & "<BR>"
      Next
	Else
	  File.WriteLine "None"
    End If
  End If
End Sub
