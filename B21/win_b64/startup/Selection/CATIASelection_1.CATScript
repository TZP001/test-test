Language="VBSCRIPT"
' The goal of this macro is to illustrate the use of the following methods
' on CATIASelection: SelectElement2, Count, Item 

Sub CATMain()

  'Definition of a list of types for objects
	Dim listOfTypes(1)
	listOfTypes(0)="Body"
  listOfTypes(1)="Hole"

	Dim myDocument
	Set myDocument = CATIA.ActiveDocument

	Dim mySelection As Selection
	Set mySelection = myDocument.Selection

  'If the selection does not contain any Body or Hole, then the following message 
  'appears in the bottom left corner of the application, and the script execution 
  'resumes as soon as a correct object has been selected.
  'The SelectElement2 method fills the selection with SelectedElement objects whose Value property is of the 
  'specified type, as mentionned in the listOfTypes list.
	Dim str As String
	str=mySelection.SelectElement2(listOfTypes,"Select a Body or a Hole",true)

  'Computes the number of Bodies or Holes that have been selected
	Dim number
	number = mySelection.Count
  msgbox "Number of Bodies and Holes selected: " & Cstr(number) 

  'Since there is no more temporary set of objects, the Count and Item methods apply 
  'to the whole selection.
  number = mySelection.Count
  msgbox "Total number of objects in the selection: " & Cstr(number) 


  'Now, we retrieve each object from the selection
	Dim selectedElement As SelectedElement
	for i=1 to number
    Set selectedElement = mySelection.Item(i)
    msgbox "Object " & Cstr(i) & "/" & Cstr(number) & "retrieved."
	next

End Sub
