'********************************************************************
'********************************************************************
'****  VBSCRIPT MACRO FOR THE GENERATION OF HTML DOCUMENTATION   ****
'****           gdu, new script CXR7 06-2001                     ****
'********************************************************************
'********************************************************************
'Problem with the link when the strings (Activity.name fe) have space character 
'file are well generated but links on them don't work
'TOFIX



Language="VBSCRIPT"

Dim OutRef As String
Dim OutPath As String
Dim IndexFileName As String
Dim RootActivityNameRef As String

'debut modif gdu
Dim fs As FileSystem
Dim folderDoc As Folder	
Dim ActFile as File
Dim IndexFile As File



Sub CATMain()
	MsgBox "This Macro can not be run directly"
	'OutPath = "/tmp/TestGenDoc/"	
	'OutRef = "TestGenerationDocGDU"
	'RootActivityNameRef = "Process"

   	'CATDocument RootActivityNameRef, OutRef, OutPath  
End Sub



'--------------------------------------------------------------------
' Main Procedure
'--------------------------------------------------------------------
Sub CATDocument( RootActivityName , HtmlFilesName , HtmlPath )
CATIA.SystemService.Print "RootActivityName : " & RootActivityName
CATIA.SystemService.Print "HtmlFilesName : " & HtmlFilesName
CATIA.SystemService.Print "HtmlFilesPath : " & HtmlPath

	OutRef=HtmlFilesName
	OutPath=HtmlPath
	RootActivityNameRef=RootActivityName

	Set fs = CATIA.FileSystem	
	'Create Doc Folder 

	If (fs.FolderExists(HtmlPath)) Then 
		Set folderDoc = fs.GetFolder(HtmlPath)
		CATIA.SystemService.Print "Folder already created "	
	Else
		Set folderDoc = fs.CreateFolder(HtmlPath)
		CATIA.SystemService.Print "Folder created :" & HtmlPath
	End If


	Dim RootActivityRef As AnyObject
  	Set RootActivityRef = Catia.ActiveDocument.GetItem(RootActivityName)

  	SPPCreateIndex RootActivityRef, HtmlPath, OutRef

	'CleanAll
End Sub




Sub CleanAll
	
	Dim files0 As Files
	Dim filetmp As File
	Dim count, i As long
	Dim string1 As String
	
	Set files0 = folderDoc.Files
	count = files0.Count
	CATIA.SystemService.Print "Generated Files count" & count
	
	for i=1 to count
		Set filetmp = files0.Item(i)
		string1 = filetmp.Name 
		
		fs.DeleteFile HTMLPath & string1
		CATIA.SystemService.Print "Delete File " & HTMLPath & string1
	next

	fs.DeleteFolder HTMLPath
	CATIA.SystemService.Print "Delete Folder" & HTMLPath

End Sub 



'---------------------------------------------------------------
' Create the index file
'---------------------------------------------------------------'
Sub SPPCreateIndex(RootActivityRef As AnyObject, HtmlPath, HtmlFilesName)

	IndexFileName = OutRef & "_index.html"

  	IndexFileCompletePath = HtmlPath & IndexFileName	

	Dim IndexFileStream As TextStream	
	
	Set IndexFile = fs.CreateFile(IndexFileCompletePath , True)
	CATIA.SystemService.Print "File Index created " & IndexFileCompletePath
	Set IndexFileStream = IndexFile.OpenAsTextStream("ForWriting")

		  'Write index file header
  IndexFileStream.Write "<!doctype html public ""-//w3c//dtd html 4.0 transitional//en"">"
  IndexFileStream.Write "<html>"
  IndexFileStream.Write "<head>"
  IndexFileStream.Write "   <meta http-equiv=""Content-Type"" content=""text/html; charset=iso-8859-1"">"
  IndexFileStream.Write "   <meta name=""GENERATOR"" content=""IPD v2"">"
  IndexFileStream.Write "   <meta name=""Author"" content=""IPD v2"">"
  IndexFileStream.Write "   <title>Activities Index for Process : " & RootActivityRef.Name & "</title>"
  IndexFileStream.Write "</head>"
  IndexFileStream.Write "<body background=""back.gif"" bgcolor=#EEEEFF>"

  IndexFileStream.Write "<CENTER>"
  IndexFileStream.Write "<P><h2>Activities Index for Process : <I>" & RootActivityRef.Name & "</I></h2>"
  IndexFileStream.Write "<I>Generation Date : " & Date & " at " & Time & "</I></P>"

  IndexFileStream.Write "</CENTER>"
  IndexFileStream.Write "<P><TABLE BORDER COLS=1 WIDTH=""100%"" >"
  IndexFileStream.Write "<TR ALIGN=CENTER BGCOLOR=#CCCCCC><TD><B>Activities Hierarchy</B></TD></TR></TABLE>"
  IndexFileStream.Write "<TABLE BORDER COLS=5 WIDTH=""100%"" >"
  IndexFileStream.Write "<TR ALIGN=CENTER BGCOLOR=#EEEEEE>"
  IndexFileStream.Write "<TD WIDTH=""30%""><B>Name</B></TD>"
  IndexFileStream.Write "<TD WIDTH=""40%""><B>Description</B></TD>"
  IndexFileStream.Write "<TD WIDTH=""10%""><B>Cycle Time</B></TD>"
  IndexFileStream.Write "<TD WIDTH=""10%""><B>Begin Date</B></TD>"
  'IndexFileStream.Write "<TD WIDTH=""10%""><B>End Date</B></TD>"
  IndexFileStream.Write "</TR>"

  'Write reference
  SPPWriteIndexRef RootActivityRef, 0,IndexFileStream
  IndexFileStream.Write "</TD></TR></TABLE></P>"

  'Generate the index image file
  'If (RootActivityRef.Parent.Name <> CATIA.ActiveDocument.Name) Then
  'Else
    'IndexFileStream.Write "<P><TABLE BORDER COLS=1 WIDTH=""100%"" >"
    'IndexFileStream.Write "<TR ALIGN=CENTER BGCOLOR=#CCCCCC><TD><B>Activities Sequence</B>"
    'IndexFileStream.Write "</TD></TR></TABLE>"
    'CATIA.ActiveWindow.ActiveViewer.Reframe
    'thename = OutPath & OutRef & ".jpg"
    'CATIA.ActiveWindow.ActiveViewer.CaptureToFile 5, thename
    'IndexFileStream.Write "<P><CENTER><IMG SRC=""file:" & thename & """</CENTER></P>"
  'End If

  'Write index file footer

  IndexFileStream.Close

End Sub

'---------------------------------------------------------------
' Write the index reference for an activity
'---------------------------------------------------------------
Sub SPPWriteIndexRef(ActivityRef As AnyObject, Level As Integer, IndexFileStream )
  Dim childs As Activities
  Dim child As Activity
  Dim quantity As Integer
  Dim I
  Dim oVal
  Dim ret
  Dim NewLevel As Integer

	

   If (ActivityRef.IsSubTypeOf("PhysicalActivity")) Then

    'Write reference for the activity itself
	'Problem with the link when ActivityRef.Name have space character 
	'TOFIX
    IndexFileStream.Write "<TR VALIGN=TOP BGCOLOR=#FFFFFF><TD><A HREF = """ & OutRef & "_" & ActivityRef.Name & ".html"">"
	'Indent the name according to the level of the activity
	Dim J
	For J = 0 To Level
	  IndexFileStream.Write "--"
	Next
	IndexFileStream.Write ActivityRef.Name & "</A></TD>"
	IndexFileStream.Write "<TD>" & ActivityRef.Description & "</TD>"
	IndexFileStream.Write "<TD>" & ActivityRef.CycleTime & "</TD>"
	IndexFileStream.Write "<TD>" & ActivityRef.BeginningDate & "</TD>"
On Error Resume Next
    'IndexFileStream.Write "<TD>" & ActivityRef.EndDate & "</TD>"
	IndexFileStream.Write "</TR>"

    'Write the activity detail file
    SPPWriteActivityFile ActivityRef

    'Write the list
    Set childs = ActivityRef.ChildrenActivities
    quantity = childs.Count

    if quantity <= 0 then
      Exit Sub
    End if
    'Recursively write sons
    For I=1 To quantity
      Set child = childs.Item(I)
      NewLevel = Level+1
      Dim TestVince As Activity
      Dim VinceLevel As Integer
      VinceLevel = 0
      Catia.SystemService.Print "--++**  DEBUT DE MacroIDL.CATScript  **++--"
      SPPWriteIndexRef child, VinceLevel,IndexFileStream
    Next
  End if

End Sub

'---------------------------------------------------------------
' Write the activity file
'---------------------------------------------------------------
Sub SPPWriteActivityFile(ActivityRep As AnyObject )
Dim ActfileName as String
Dim ActFilestream As TextStream

	ActfileName = OutPath & OutRef & "_" & ActivityRep.Name & ".html"
	Set ActFile = fs.CreateFile(ActfileName , True)
	CATIA.SystemService.Print "Act File created " & ActfileName
	Set ActFilestream =ActFile.OpenAsTextStream("ForWriting")
  

	SPPWriteHeader ActivityRep,ActFilestream 
  	SPPWriteCore ActivityRep,ActFilestream
  	SPPWriteFooter ActivityRep,ActFilestream

End Sub

'---------------------------------------------------------------
' Write an activity file header
'---------------------------------------------------------------
Sub SPPWriteHeader(ActivityRep As AnyObject, ActFilestream)
  
	ActFilestream.Write "<!doctype html public ""-//w3c//dtd html 4.0 transitional//en"">"
  ActFilestream.Write "<html>"
  ActFilestream.Write "<head>"
  ActFilestream.Write "   <meta http-equiv=""Content-Type"" content=""text/html; charset=iso-8859-1"">"
  ActFilestream.Write "   <meta name=""GENERATOR"" content=""IPD v2"">"
  ActFilestream.Write "   <meta name=""Author"" content=""IPD v2"">"
  ActFilestream.Write "   <title>Activity Detail : " & ActivityRep.Name & "</title>"
  ActFilestream.Write "</head>"
  ActFilestream.Write "<body background=""back.gif"" bgcolor=#EEEEFF>"

  ActFilestream.Write "<CENTER>"
  ActFilestream.Write "<P><h2>Activity Detail : <I>" & ActivityRep.Name & "</I></h2>"
  ActFilestream.Write "<I>Generation Date : " & Date & " at " & Time & "</I></P>"

  ActFilestream.Write "</CENTER>"
End Sub

'---------------------------------------------------------------
' Write an activity file core
'---------------------------------------------------------------
Sub SPPWriteCore(ActivityRep As AnyObject, ActFilestream)
  ActFilestream.Write "<P><TABLE BORDER COLS=2 WIDTH=""100%"" >"
  ActFilestream.Write "<TR ALIGN=CENTER BGCOLOR=#CCCCCC><TD><B>General Data</B></TD><TD><B>Specific Data</B></TD></TR>"
  ActFilestream.Write "<TR VALIGN=TOP BGCOLOR=#FFFFFF>"
  ActFilestream.Write "<TD><B>Name : </B>" & ActivityRep.Name & "<BR>"
  ActFilestream.Write "<B>Type : </B>" & ActivityRep.Type & "<BR>"
  ActFilestream.Write "<B>Description : </B>" & ActivityRep.Description & "<BR>"
  ActFilestream.Write "<B>Cycle Time : </B>" & ActivityRep.CycleTime & "<BR>"
  ActFilestream.Write "<B>Calculated Cycle Time : </B>" & ActivityRep.CalculatedCycleTime & "<BR>"
  ActFilestream.Write "<B>Begin Date : </B>" & ActivityRep.BeginningDate & "<BR>"
On Error Resume Next
  'ActFilestream.Write "<B>End Date : </B>" & ActivityRep.EndDate & "<BR>"
  ActFilestream.Write "</TD>"
  'SUB for specific data
  ActFilestream.Write "<TD>"
  SPPWriteSpecific ActivityRep,ActFilestream
  ActFilestream.Write "</TD>"
  ActFilestream.Write "</TR>"
  ActFilestream.Write "</TABLE></P>"

  ActFilestream.Write "<P><TABLE BORDER COLS=2 WIDTH=""100%"" >"
  ActFilestream.Write "<TR ALIGN=CENTER BGCOLOR=#CCCCCC><TD><B>Items List</B></TD><TD><B>Resources List</B></TD></TR>"
  'SUB for items list
  ActFilestream.Write "<TR VALIGN=TOP BGCOLOR=#FFFFFF><TD>"
  SPPWriteItems ActivityRep,ActFilestream
  ActFilestream.Write "</TD>"
  'SUB for resources list
  ActFilestream.Write "<TD>"
  SPPWriteResources ActivityRep,ActFilestream
  ActFilestream.Write "</TD>"
  ActFilestream.Write "</TR>"
  ActFilestream.Write "</TABLE></P>"
End Sub

'---------------------------------------------------------------
' Write an activity item list
'---------------------------------------------------------------
Sub SPPWriteItems(ActivityRef As AnyObject, ActFilestream)
  Dim items_var As Items
  Dim item As Item
  Dim quantity As Integer
  Set items_var = ActivityRef.Items
  quantity = items_var.Count
  if quantity <= 0 then
    ActFilestream.Write "None"
    exit sub
  end if
  ActFilestream.Write "<UL>"
  For I=1 To quantity
    Set item = items_var.Item(I)
	ActFilestream.Write "<LI>" & item.Name & "</LI>"
  Next
  ActFilestream.Write "</UL>"
End Sub

'---------------------------------------------------------------
' Write an activity resource list
'---------------------------------------------------------------
Sub SPPWriteResources(ActivityRep As AnyObject, ActFilestream)
  Dim items_var As Resources
  Dim item As Resource
  Dim quantity As Integer
  Set items_var = ActivityRep.Resources
  quantity = items_var.Count
  if quantity <= 0 then
    ActFilestream.Write "None"
    exit sub
  end if
  ActFilestream.Write "<UL>"
  For I=1 To quantity
    Set item = items_var.Item(I)
	ActFilestream.Write "<LI>" & item.Name & "</LI>"
  Next
  ActFilestream.Write "</UL>"
End Sub

'---------------------------------------------------------------
' Write an activity file footer
'---------------------------------------------------------------
Sub SPPWriteFooter(ActivityRef As AnyObject, ActFilestream)
  ActFilestream.Write "<P><TABLE BORDER COLS=1 WIDTH=""100%"" >"
  ActFilestream.Write "<TR ALIGN=CENTER BGCOLOR=#CCCCCC><TD><B>Related Activities</B></TD></TR></TABLE>"

  ActFilestream.Write "<TABLE BORDER COLS=4 WIDTH=""100%"" >"
  ActFilestream.Write "<TR VALIGN=TOP BGCOLOR=#FFFFFF>"
  ActFilestream.Write "<TD><B><<<< Previous</B>"
  ' SPPWritePrevious ActivityRef, File
  SPPWritePrevious ActivityRef,ActFilestream
  ActFilestream.Write "</TD>"

  'ActFilestream.Write "<TD><B>Parent</B>"
  'ActFilestream.Write "<BR><A HREF = """ & "bidon.html" & """>" & "parent_name" & "</A></TD>"
  'ActFilestream.Write "</TD>"

  ActFilestream.Write "<TD><B>Childs</B>"
  SPPWriteChilds ActivityRef,ActFilestream
  ActFilestream.Write "</TD>"

  ActFilestream.Write "<TD><B>Next >>>></B>"
  SPPWriteNext ActivityRef,ActFilestream
  ActFilestream.Write "</TD>"

  ActFilestream.Write "</TR>"
  ActFilestream.Write "</TABLE></P>"

	'Problem with the link when IndexFileName has space character 
	'TOFIX
  ActFilestream.Write "<P><B><I><A HREF = """ & IndexFileName & """>Activities Index</I></B>"

End Sub

'---------------------------------------------------------------
' Write the previous list
'---------------------------------------------------------------
Sub SPPWritePrevious(ActivityRep As AnyObject, ActFilestream)
  Dim activities As Activities
  Dim one As Activity
  Dim quantity As Integer
  Dim I

  Set activities = ActivityRep.PreviousCFActivities
  quantity = activities.Count
  if quantity <= 0 then
    exit sub
  end if
   ActFilestream.Write "<UL>"
  for I = 1 to quantity
    Set one = activities.Item(I)
    If (one.IsSubTypeOf("PhysicalActivity")) Then
	'Problem with the link when one.Name has space character 
	'TOFIX
      ActFilestream.Write "<LI><A HREF = """ & OutRef & "_" & one.Name & ".html" & """>" & one.Name & "</A></LI>"
    End If
       Dim oneTypeString
       oneTypeString = one.Type
    If ((oneTypeString = "AndIn") Or (oneTypeString = "OrIn") Or (oneTypeString = "Switch") Or (oneTypeString = "AndOut")) then
	  ActFilestream.Write "<LI><I><B>" & one.Type & "</B></I></LI>"
	  'WritePrevious one, File
	  SPPWritePrevious one, ActFilestream
    End If
  next
  ActFilestream.Write "</UL>"
End Sub

'---------------------------------------------------------------
' Write the Childs list
'---------------------------------------------------------------
Sub SPPWriteChilds(ActivityRep As AnyObject, ActFilestream)
  Dim activities As Activities
  Dim one As Activity
  Dim quantity
  Dim I

  Set activities = ActivityRep.ChildrenActivities
  quantity = activities.Count
  if quantity <= 0 then
    exit sub
  end if

  ActFilestream.Write "<UL>"
  for I = 1 to quantity
    Set one = activities.Item(I)
    If (one.IsSubTypeOf("PhysicalActivity")) Then
	'Problem with the link when one.Name has space character 
	'TOFIX
	  ActFilestream.Write "<LI><A HREF = """ & OutRef & "_" & one.Name & ".html" & """>" & one.Name & "</A></LI>"
	End If
  next
  ActFilestream.Write "</UL>"
End Sub

'---------------------------------------------------------------
' Write the next list
'---------------------------------------------------------------
Sub SPPWriteNext(ActivityRep As AnyObject, ActFilestream)
  Dim activities As Activities
  Dim one As Activity
  Dim quantity As Integer
  Dim I

  Set activities = ActivityRep.NextCFActivities
  quantity = activities.Count
  if quantity <= 0 then
    exit sub
  end if

  ActFilestream.Write "<UL>"
  for I = 1 to quantity
    Set one = activities.Item(I)
    If (one.IsSubTypeOf("PhysicalActivity")) Then
	  ActFilestream.Write "<LI><A HREF = """ & OutRef & "_" & one.Name & ".html" & """>" & one.Name & "</A></LI>"
    End If
    Dim oneTypeString
    oneTypeString = one.Type
    If (oneTypeString = "AndOut") Or (oneTypeString = "Switch") Or (oneTypeString = "AndIn") Or (oneTypeString = "OrIn") then
	  ActFilestream.Write "<LI><I><B>" & one.Type & "</B></I></LI>"
	  ' WriteNext one, File
	  SPPWriteNext one,ActFilestream
    End If
  next
  ActFilestream.Write "</UL>"
End Sub

'---------------------------------------------------------------
' Write an activity file specific data block
'---------------------------------------------------------------
Sub SPPWriteSpecific(ActivityRep As AnyObject, ActFilestream)
  Dim Nbr As Integer
  Dim Attributename
  If (ActivityRep.IsSubTypeOf("PhysicalActivity")) Then
    Nbr=ActivityRep.AttrCount
    If (Nbr > 0) Then
      For I=1 To Nbr
        Attributename = ActivityRep.AttrName(I)
        ActFilestream.Write "<B>" & Attributename & " : </B>"
        AttrVal = ActivityRep.AttrValue(I)
        ActFilestream.Write AttrVal & "<BR>"
      Next
	Else
	  ActFilestream.Write "None"
    End If
  End If
End Sub
