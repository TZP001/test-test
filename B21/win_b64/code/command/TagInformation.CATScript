'// ---------- CATIAV5 application objects
Dim objCATIAV5Document As Document
Dim objCATIAV5Tag As Tag
Dim List(3)
Dim Name as String
Dim FrameType as String
'====================================================================================
Sub CATMain () 'Method to Set/Retrieve Tag Informations
'====================================================================================

  Set Parentobject = CATIA.ActiveDocument.Selection.FindObject("CATIAProduct")	
  Set objCATIAV5Tag =Parentobject.GetTechnologicalObject("Tag")
  msgbox("Name of the Selected Tag is")
  msgbox(objCATIAV5Tag.Name) 

  msgbox("Existing Frame Type of the Selected Tag is")
  objCATIAV5Tag.GetType FrameType
  msgbox(FrameType)
  
  objCATIAV5Tag.SetType("Design")
  msgbox("Frame Type Changed to")
  objCATIAV5Tag.GetType FrameType
  msgbox(FrameType)
 
  objCATIAV5Tag.SetName("My_Tag")
  msgbox("Name Changed to")
  objCATIAV5Tag.GetName Name
  msgbox(Name)

  objCATIAV5Tag.SetXYZ 2800.0, 1800.0, 800.0
  objCATIAV5Tag.GetXYZ List
  msgbox("Tag position changed to")
  msgbox(List(0))  
  msgbox(List(1)) 
  msgbox(List(2))  

End Sub '/////////////////////////////////////////////////////////// CATMain
