Language="VBSCRIPT"

Sub CATMain(NbHoles,HName,HDiam,HTole,HDept,HLocX,HLocY,HLocZ,HAxeX,HAxeY,HaxeZ,HType,HBlin,HThrd,HThDe,HThDi,HThPi,HThSi,HHDia,HHDep,HHAng,HBTyp,HBAng,HAnch,Plate)


 	Dim Doc As Document
 	Set Doc = CATIA.Documents.NewFrom(Plate)
'Doc.update


'--------------------------------------------------------------------------------------------------------------------
' body creation
'--------------------------------------------------------------------------------------------------------------------

    Dim partDocument1 As PartDocument
    Dim part1 As Part

    Dim ShapeFactory1 As ShapeFactory
    Dim hybridShapeFactory1 As HybridShapeFactory
    Dim bodies1 As Bodies
    Dim body1 As Body

    Set partDocument1 = CATIA.ActiveDocument
    Set part1 = partDocument1.Part

    Dim oBodis As Bodies
    Set oBodis = part1.Bodies
    Dim j As Integer
    j = oBodis.Count
    Set bodis1 = part1.Bodies
    Set bod1 = bodis1.Add()
    bod1.Name = "Body_to_make_hole"
    Set hybridBodies1 = bod1.HybridBodies
    Set hybridBody1 = hybridBodies1.Add
    hybridBody1.Name = "Offset_body"

    'asking user to select a Face
    Set Selection = partDocument1.Selection
    Set Selection2 = partDocument1.Selection
    Set hybridShapeFactory1 = part1.HybridShapeFactory
    ReDim sFilter(0)

	' Added by cvr to manage ODT
	Dim mySystemService
	Set mySystemService = CATIA.SystemService
	Dim RemoveBox As String
	RemoveBox = mySystemService.Environ("MFG_REMOVE_MSGBOX")
	mySystemService.Print "Remove MsgBox=" & RemoveBox
    If RemoveBox = "" Then
	    MsgBox "Select a Face of the plate"
	End If
    sFilter(0) = "Face"
    sStatus = Selection2.SelectElement2(sFilter, "select a face", False)
        If (sStatus = "Cancel") Then
            Exit Sub
        End If
'--------------------------------------------------------------------------------------------------------------------
    'extract creation 
'--------------------------------------------------------------------------------------------------------------------

    Set ref_face = Selection2.Item(1).Value
    Dim hybridShapeExtract1 As HybridShapeExtract
    Set hybridShapeExtract1 = hybridShapeFactory1.AddNewExtract(ref_face)
    hybridShapeExtract1.PropagationType = 1
    hybridShapeExtract1.ComplementaryExtract = False
    hybridShapeExtract1.IsFederated = False
    hybridBody1.AppendHybridShape hybridShapeExtract1
    part1.InWorkObject = hybridShapeExtract1
    Set reference1 = hybridShapeExtract1
    part1.Update
'--------------------------------------------------------------------------------------------------------------------
    'Offset creation
'--------------------------------------------------------------------------------------------------------------------

    Dim hybridShapeOffset1 As HybridShapeOffset
    Set hybridShapeOffset1 = hybridShapeFactory1.AddNewOffset(reference1, 0.02, False, 0.01)
    hybridBody1.AppendHybridShape hybridShapeOffset1
    part1.InWorkObject = hybridShapeOffset1
    Set reference1 = hybridShapeOffset1

    '--------------------------------------------------------------------------------------------------------------------
    '  extremums creation
    '--------------------------------------------------------------------------------------------------------------------
   
 Dim hybridShapeD1, hybridShapeD2, hybridShapeD3 As HybridShapeDirection
    
    'definition of X, Y et Z

    Set hybridShapeD1 = hybridShapeFactory1.AddNewDirectionByCoord(1, 0, 0)
    Set hybridShapeD2 = hybridShapeFactory1.AddNewDirectionByCoord(0, 1, 0)
    Set hybridShapeD3 = hybridShapeFactory1.AddNewDirectionByCoord(0, 0, 1)

    Set HybridShapeExtremum1 = hybridShapeFactory1.AddNewExtremum(reference1, hybridShapeD1, 1)
    Set HybridShapeExtremum2 = hybridShapeFactory1.AddNewExtremum(reference1, hybridShapeD1, 0)
    Set hybridShapeExtremum3 = hybridShapeFactory1.AddNewExtremum(reference1, hybridShapeD2, 1)
    Set hybridShapeExtremum4 = hybridShapeFactory1.AddNewExtremum(reference1, hybridShapeD2, 0)
    Set hybridShapeExtremum5 = hybridShapeFactory1.AddNewExtremum(reference1, hybridShapeD3, 1)
    Set hybridShapeExtremum6 = hybridShapeFactory1.AddNewExtremum(reference1, hybridShapeD3, 0)
    part1.Update


    hybridBody1.AppendHybridShape HybridShapeExtremum1
    part1.InWorkObject = HybridShapeExtremum1
    HybridShapeExtremum1.Name = "max_X"
    hybridBody1.AppendHybridShape HybridShapeExtremum2
    part1.InWorkObject = HybridShapeExtremum2
    HybridShapeExtremum2.Name = "min_X"
    hybridBody1.AppendHybridShape hybridShapeExtremum3
    part1.InWorkObject = hybridShapeExtremum3
    hybridShapeExtremum3.Name = "max_Y"
    hybridBody1.AppendHybridShape hybridShapeExtremum4
    part1.InWorkObject = hybridShapeExtremum4
    hybridShapeExtremum4.Name = "min_Y"
    hybridBody1.AppendHybridShape hybridShapeExtremum5
    part1.InWorkObject = hybridShapeExtremum5
    hybridShapeExtremum5.Name = "max_Z"
    hybridBody1.AppendHybridShape hybridShapeExtremum6
    part1.InWorkObject = hybridShapeExtremum6
    hybridShapeExtremum6.Name = "min_Z"
    part1.Update

    Dim Ref1, Ref2, Ref3, Ref4, Ref5, Ref6  As Reference
    Dim Point1, Point2, Point3, Point4, Point5, Point6 As HybridShapePointCoord
    Set Ref1 = part1.CreateReferenceFromObject(HybridShapeExtremum1)

    Set Point1 = hybridShapeFactory1.AddNewPointCoordWithReference(0, 0, 0, Ref1)
    hybridBody1.AppendHybridShape Point1
    Set Ref2 = part1.CreateReferenceFromObject(HybridShapeExtremum2)
    Set Point2 = hybridShapeFactory1.AddNewPointCoordWithReference(0, 0, 0, Ref2)
    hybridBody1.AppendHybridShape Point2
    Set Ref3 = part1.CreateReferenceFromObject(hybridShapeExtremum3)
    Set Point3 = hybridShapeFactory1.AddNewPointCoordWithReference(0, 0, 0, Ref3)
    hybridBody1.AppendHybridShape Point3
    Set Ref4 = part1.CreateReferenceFromObject(hybridShapeExtremum4)
    Set Point4 = hybridShapeFactory1.AddNewPointCoordWithReference(0, 0, 0, Ref4)
    hybridBody1.AppendHybridShape Point4
    Set Ref5 = part1.CreateReferenceFromObject(hybridShapeExtremum5)
    Set Point5 = hybridShapeFactory1.AddNewPointCoordWithReference(0, 0, 0, Ref5)
    hybridBody1.AppendHybridShape Point5
    Set Ref6 = part1.CreateReferenceFromObject(hybridShapeExtremum6)
    Set Point6 = hybridShapeFactory1.AddNewPointCoordWithReference(0, 0, 0, Ref6)
    hybridBody1.AppendHybridShape Point6
    
    part1.Update

    Dim pt1, pt2, pt3, pt4, pt5, pt6  As Point
    Set pt1 = Point1
    pt1.Name = "MaxX"
    ReDim Start(2) As Double
    pt1.GetCoordinates Start
    Dim xmax
    xmax = Start(0)
    Set pt2 = Point2
    pt2.Name = "MinX"
    pt2.GetCoordinates Start
    Dim xmin
    xmin = Start(0)
    Set pt3 = Point3
    pt3.Name = "MaxY"
    pt3.GetCoordinates Start
    Dim ymax
    ymax = Start(1)
    Set pt4 = Point4
    pt4.Name = "MinY"
    pt4.GetCoordinates Start
    Dim ymin
    ymin = Start(1)
    Set pt5 = Point5
    pt5.Name = "MaxZ"
    pt5.GetCoordinates Start
    Dim zmax
    zmax = Start(2)
    Set pt6 = Point6
    pt6.Name = "MinZ"
    pt6.GetCoordinates Start
    Dim zmin
    zmin = Start(2)
    
    Dim localOrigin As HybridShapePointCoord
    Dim x_localOrigin, y_localOrigin, z_localOrigin   As Double
    x_localOrigin = (xmax + xmin) / 2
    y_localOrigin = (ymax + ymin) / 2
    z_localOrigin = zmax
    Set localOrigin = hybridShapeFactory1.AddNewPointCoord(x_localOrigin, y_localOrigin, z_localOrigin)
    hybridBody1.AppendHybridShape localOrigin
    localOrigin.Name = "LocalOrigin"
    Set ref_localOrigin = part1.CreateReferenceFromObject(localOrigin)
    
    part1.Update
    Dim local_axis
    Set local_axis = part1.AxisSystems.Add()
    
    local_axis.Type = 0
    local_axis.OriginPoint = ref_localOrigin
    local_axis.IsCurrent = True

    '--------------------------------------------------------------------------------------------------------------------
    'creation de la close surface
    '--------------------------------------------------------------------------------------------------------------------

    Set ShapeFactory1 = part1.ShapeFactory
    Dim closeSurface1 As CloseSurface
    Set closeSurface1 = ShapeFactory1.AddNewCloseSurface(reference1)
    closeSurface1.Name = "to_drill"
    Set reference1 = closeSurface1
    'mis en noshow l'open body cree
    Selection.Clear
    Selection.Add (hybridBody1)
    Selection.Add (closeSurface1)
    Selection.Add (local_axis)
    Selection.VisProperties.SetShow catVisPropertyNoShowAttr
    Selection.Clear

    part1.Update

    Dim Dirx, Diry, Dirz, Coordx, Coordy, Coordz As Double


    Dim ino As Integer


For ino = 0 To NbHoles
  	  Dirx = HAxeX(ino)
        Diry = HAxeY(ino)
        Dirz = HAxeZ(ino)
    
        Coordx = HLocX(ino)
        Coordy = HLocY(ino)
        Coordz = HLocZ(ino)
    
        HoleType = HType(ino)
        HoleDiameter = HDiam(ino)
        HoleTolerance = HTole(ino)
        HoleDepth = HDept(ino)
        Holeblindthrough = HBlin(ino)
        HoleThreadedorNot = HThrd(ino)
        HoleThreadedDiameter = HThDi(ino)
        HoleThreadedDepth = HThDe(ino)
        HoleThreadedPitch = HThPi(ino)
        HoleThreadedSide = HThSi(ino)
        HoleHeadDiameter = HHDia(ino)
        HoleHeadDepth = HHDep(ino)
        HoleHeadAngle = HHAng(ino)
        HoleBottomType = HBTyp(ino)
        HoleBottomAngle = HBAng(ino)
        HoleAnchorMode = HAnch(ino)
        Set hybridShapeD1 = hybridShapeFactory1.AddNewDirectionByCoord(Dirx, Diry, Dirz)
        Set reference1 = part1.CreateReferenceFromObject(closeSurface1)
        
    
        '---------------------------------------------Origin & directions
        
        Dim oOrigin As HybridShapePointCoord
        Set oOrigin = hybridShapeFactory1.AddNewPointCoordWithReference(Coordx, Coordy, Coordz, ref_localOrigin)
        hybridBody1.AppendHybridShape oOrigin
        Dim ref_oOrigin As Reference
        Set ref_oOrigin = part1.CreateReferenceFromObject(oOrigin)
        Dim holedirref_1 As HybridShapeLinePtDir
        Set holedirref_1 = hybridShapeFactory1.AddNewLinePtDir(oOrigin, hybridShapeD1, 0, 2, True)
        hybridBody1.AppendHybridShape holedirref_1
        Dim ref_plane As Reference
        Set ref_plane = part1.CreateReferenceFromObject(holedirref_1)
        Dim plan_support As HybridShapePlaneNormal
        Set plan_support = hybridShapeFactory1.AddNewPlaneNormal(ref_plane, oOrigin)
        hybridBody1.AppendHybridShape plan_support
        set ref_plan_support =  part1.CreateReferenceFromObject(plan_support)
        Set plan_support_hole = hybridShapeFactory1.AddNewPlaneOffset(ref_plan_support, 0.02,1)
	  hybridBody1.AppendHybridShape plan_support_hole
        
        Dim reference1 As Reference
        Set reference1 = part1.CreateReferenceFromObject(oOrigin)
        
        Dim reference2 As Reference
        Set reference2 = part1.CreateReferenceFromObject(plan_support_hole )
        part1.Update
        Dim OutHole As Hole
        Set OutHole = ShapeFactory1.AddNewHoleFromRefPoint(reference1, reference2, HoleDiameter)
		
        OutHole.Reverse

	  if Holeblindthrough = "Blind" then
		OutHole.BottomLimit.LimitMode=catOffsetLimit
		OutHole.BottomLimit.Dimension.Value= HoleDepth
		if HoleBottomType = "V" then
			OutHole.BottomType = catVHoleBottom
			OutHole.BottomAngle.value=HoleBottomAngle
		else
			OutHole.BottomType = catFlatHoleBottom
	 	end if
	  else 
		OutHole.BottomLimit.LimitMode=catUpToLastLimit
	  end if


	  if HoleType = "Simple" then
		OutHole.Type = catSimpleHole
		OutHole.Diameter.Value = HoleDiameter
		
		
	  elseif HoleType =  "Tapered" then
		OutHole.Type = catSimpleHole
		OutHole.Diameter.Value = HoleDiameter
		OutHole.Type = catTaperedHole
		OutHole.HeadAngle.value = HoleHeadAngle


	  elseif HoleType = "Counterbored" then
		OutHole.Type = catCounterboredHole
		OutHole.Diameter.Value = HoleDiameter
		OutHole.HeadDiameter.value=HoleHeadDiameter
		OutHole.HeadDepth.value= HoleHeadDepth
		if HoleAnchorMode = "Top of its head" then
			OutHole.AnchorMode = catExtremPointHoleAnchor
		elseif HoleAnchorMode = "Bottom of its head" then
			OutHole.AnchorMode = catMiddlePointHoleAnchor
		end if

	  elseif HoleType = "Countersunk" then
		OutHole.Type = catCountersunkHole
		OutHole.Diameter.Value = HoleDiameter
		OutHole.CounterSunkMode =catCSModeDepthAngle
		OutHole.HeadDepth.value = HoleHeadDepth
		OutHole.HeadAngle.value = HoleHeadAngle

	  elseif HoleType = "Counterdrilled" then
		OutHole.Type = catCounterdrilledHole
		OutHole.Diameter.Value = HoleDiameter
		OutHole.HeadDiameter.value = HoleHeadDiameter
		OutHole.HeadAngle.value = HoleHeadAngle
		OutHole.HeadDepth.value = HoleHeadDepth		
		if HoleAnchorMode = "Top of its head" then
			OutHole.AnchorMode = catExtremPointHoleAnchor
		elseif HoleAnchorMode = "Bottom of its head" then
			OutHole.AnchorMode = catMiddlePointHoleAnchor
		end if

	  end if
		
	  if HoleThreadedorNot = "Threaded" then
		OutHole.ThreadingMode=CATThreadedHolethreading
		OutHole.ThreadDiameter.value = HoleThreadedDiameter
		OutHole.ThreadDepth.value=HoleThreadedDepth 
		OutHole.ThreadPitch.value = HoleThreadedPitch

		if HoleThreadedSide = "Left-Threaded" then
			OutHole.ThreadSide = catLeftThreadSide

		elseif HoleThreadedSide = "Right-Threaded" then
			OutHole.ThreadSide = catRightThreadSide

		end if

	  elseif HoleThreadedorNot = "Not Threaded" then
		OutHole.ThreadingMode=catSmoothHoleThreading

	  end if
'loop to test if a tolerance exists and create a parameter if it's the case


'dim HoleTol as boolean
'if HoleTolerance ="" then
'	HoleTol = False
	
'else
'	HoleTol = True
	set parameters1 = part1.parameters
	set par1=parameters1.createString("Tolerance_"&outHole.name, HoleTolerance)
'end if


next
part1.Update 

Dim Message2, Style2, Title2, Response2, MyString2
Message2 = ("Do you want to create Machinig Patterns  ?")
Style2 = vbYesNo + vbDefaultButton2    'Define buttons.
Title2 = "Purpose "

' Added by cvr to manage ODT
Response2 = vbYes
If RemoveBox = "" Then
	Response2 = MsgBox(Message2, Style2, Title2)
End If

If Response2 = vbYes Then    ' User chose Yes.
	MyString2 = "Yes"
'open prismatic workbench
Dim thePartDoc As Document
Set thePartDoc = CATIA.ActiveDocument
Dim theProduct As Product
Set theProduct = thePartDoc.Product

CATIA.Documents.Add "Process"
Dim thePPRDoc As Document
Set thePPRDoc = CATIA.ActiveDocument
Dim theApplication As Application
Set theApplication = thePPRDoc.Application
theApplication.StartWorkbench ("ManufacturingProgramWorkbench")

Dim theProcess As AnyObject
Set theProcess = thePPRDoc.GetItem("Process")

Dim theSetup As ManufacturingSetup

If (theProcess.IsSubTypeOf("PhysicalActivity")) Then
	Set Childs = theProcess.ChildrenActivities
	quantity = Childs.Count
	If quantity <= 0 Then
		Exit Sub
	End If
	NumberOfPO = 0
	For i = 1 To quantity
		Set Child = Childs.Item(i)
		If (Child.IsSubTypeOf("ManufacturingSetup")) Then
			Set theSetup = Child
			NumberOfPO = NumberOfPO + 1
			Exit For
		End If
	Next
End If
If NumberOfPO <= 0 Then
	Exit Sub
End If

theSetup.Product = theProduct

Dim MfgDoc1 As Document 
Set MfgDoc1 = CATIA.ActiveDocument 
MfgDoc1.close


    Dim sCommentHoleType As String
    Dim dDirArray(2) As Double
    Dim dDirArray1(2) As Double
    Dim dDirArray2(2) As Double
    Dim dDirArray3(2) As Double
    Dim dDirArray4(2) As Double
    Dim Coordarray(2) As Double
    Dim MyPattern As String


'***********************************************
'--------------Creating the machining pattern
'************************************************

'Retrieve the active CATPROCESS document
    'Dim MfgDoc1 As Document
    Set MfgDoc1 = CATIA.ActiveDocument

'Retrieve the current setup
    Dim ActivityRef As AnyObject
    Set ActivityRef = MfgDoc1.GetItem("Process")

    Dim Setup1 As ManufacturingSetup
    Dim Childs As ChildrenActivities
    Dim Child As ChildrenActivity
    
    If (ActivityRef.IsSubTypeOf("PhysicalActivity")) Then

        Set Childs = ActivityRef.ChildrenActivities
        Dim quantity As Count
        quantity = Childs.Count
    
        If quantity <= 0 Then
            Exit Sub
        End If
    
        Dim NumberOfSetup As Integer
        NumberOfSetup = 0

        Dim I As Integer
            For I = 1 To quantity
                Set Child = Childs.Item(I)
                    If (Child.IsSubTypeOf("ManufacturingSetup")) Then
                        Set Setup1 = Child
                        NumberOfSetup = NumberOfSetup + 1
                        Exit For
                    End If
            Next
    End If
    
    If NumberOfSetup <= 0 Then
        Exit Sub
    End If

    'Retrieve current Product linked to the current setup
    Dim Prod As Product
    Set Prod = Setup1.Product

    'Retrieve the design Pattern and the holes in the good body


    Dim myDocument As Document
    Set myDocument = CATIA.ActiveDocument
    Dim mySelection As Selection
    Set mySelection = myDocument.Selection

Dim listOfTypes(0)
	listOfTypes(0)="Part"	

	' Added by cvr to manage ODT
	If RemoveBox = "" Then
		Msgbox "Click on a Part (the plate)"
	End If

	Dim str As Part
	str=mySelection.SelectElement2(listOfTypes,"Select a Part",false)
	
		
	If (str="ok" OR str="Normal") Then
		Dim SelectedElement As selectedElement
		Set SelectedElement = mySelection.Item(1).Value
	'	Msgbox  " The selected part is : " & SelectedElement.Name
	End If

Dim bodie1 As bodies
Set bodie1= SelectedElement.bodies


    Dim dHoleDiameter As Double

   ' Select a Body
    Dim Body01 As Body
    Set Body01 = bodie1.Item("Body_to_make_hole")

    ' Retrieve Shapes in the selected Body
    Dim Shapes1 As Shapes
    Set Shapes1 = Body01.Shapes

    ' Retrieve the Shapes Collection
    Dim IJ As Integer
dim parameters1 as parameters     
set parameters1 = part1.parameters
For NbPar=1 to parameters1.Count
	For NHole=1 to Shapes1.Count
		if parameters1.Item(NbPar).Name = part1.Name&"\Tolerance_"&Shapes1.Item(NHole).Name Then
	'		msgbox "trouver"&parameters1.Item(NbPar).value
		end if
	Next
Next



         
        For IJ = 1 To Shapes1.Count

            ' The Shape is considered as a Hole
            Dim Feature As Hole
            Set Feature = Shapes1.Item(IJ)
            On Error Resume Next
            GetHoleInParameters Feature, sCommentHoleType
                If Err <> 0 Then
                    On Error GoTo 0
                Else
                    Feature.GetDirection dDirArray
                    Dim c As Integer
                    c = 0
                    Dim k As Integer
                        For k = 1 To IJ
                            On Error Resume Next
                            GetHoleInParameters Shapes1.Item(k), sCommentHoleType
                            If Err <> 0 Then
                                On Error GoTo 0
                            Else
                                Shapes1.Item(k).GetDirection dDirArray1
						For para=1 to parameters.count
							if parameters.Item(para).name = part1.Name&"\Tolerance_"&Shapes1.Item(IJ).Name And ok = False Then
								set paraTole1 = parameters1.Item(part1.Name&"\Tolerance_"&Shapes1.Item(IJ).Name)
								ok = True
							else
								ok = False
							end if
						Next

						For para1=1 to parameters.count
							if parameters.Item(para1).name = part1.Name&"\Tolerance_"&Shapes1.Item(k).Name And ok2 = False Then
							set paraTole2 = parameters1.Item(part1.Name&"\Tolerance_"&Shapes1.Item(k).Name)
							ok2 = True
							else
								ok2 = False
							end if

						Next
                                If (paraTole1.Value = paraTole2.Value And Feature.Diameter.Value = Shapes1.Item(k).Diameter.Value And FormatNumber(dDirArray(2), 2) = FormatNumber(dDirArray1(2), 2) And FormatNumber(dDirArray(1), 2) = FormatNumber(dDirArray1(1), 2) And FormatNumber(dDirArray(0), 2) = FormatNumber(dDirArray1(0), 2) And Feature.BottomLimit.LimitMode = Shapes1.Item(k).BottomLimit.LimitMode And Feature.ThreadingMode = Shapes1.Item(k).ThreadingMode And Feature.Type = Shapes1.Item(k).Type) Then
                                    c = c + 1
						
                                End If
                            End If
                        Next
' _____________________________________________________________blind threaded simple

                    If c = 1 And Feature.BottomLimit.LimitMode = catOffsetLimit And Feature.Type = catSimpleHole And Feature.ThreadingMode = catThreadedHoleThreading Then

                        'Retrieve the manufacturingview
                        Dim MfgView As ManufacturingView
                        Set MfgView = Setup1.GetManufacturingView

                      'Create a Machining Pattern
                        Dim Features As ManufacturingFeatures
                        Set Features = MfgView.ManufacturingFeatures
                
                        'Msgbox "Create pattern"
                        Dim ManPattern As ManufacturingPattern
                        Set ManPattern = Features.Add("MfgPatternUsage")
                        ManPattern.Name = "Holes" & "_" & "Diam" & Feature.Diameter.Value & "_" & "Blind" & "_" & "Threaded" & "_" & "Simple" 
                        MyPattern = "Holes" & "_" & "Diam" & Feature.Diameter.Value & "_" & "Blind" & "_" & "Threaded" & "_" & "Simple"
                        Dim l As Integer
                        For l = 1 To Shapes1.Count
                            Dim oHole As Hole
                            Set oHole = Shapes1.Item(l)
                            On Error Resume Next
                            GetHoleInParameters oHole, sCommentHoleType
                            If Err <> 0 Then
                                Dim oPattern As Pattern
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                            If Err <> 0 Then
                                                  If Feature.Diameter.Value = oPattern.ItemToCopy.ItemToCopy.Diameter.Value Then
                                                    On Error Resume Next
                                                    GetHoleInParameters oPattern.ItemToCopy.ItemToCopy, sCommentHoleType
                                                        If Err <> 0 Then
                                                            On Error GoTo 0
                                                        Else
                                                            ManPattern.AddPosition oPattern, Prod, 0
                                                        End If
                                                    End If
                                            Else
                                                ManPattern.AddPosition oPattern, Prod, 0
                                            End If
                                    End If
                                End If
                            Else
                               oHole.GetDirection dDirArray3
                               oHole.GetOrigin Coordarray
                               If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    Dim BottomTyp As String
                    
                                       If oHole.BottomType = catFlatHoleBottom Then
                                           BottomTyp = "FlatBottom"
                                       Else: BottomTyp = "VBottom"
                                       End If
 '                                   oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Simple" & ";" & "Threaded" & ";" & "Blind" & ";" & BottomTyp & ";" & MyPattern
                               End If
                           End If
                        Next

' ________________________________________________________________blind simple

                    ElseIf c = 1 And Feature.BottomLimit.LimitMode = catOffsetLimit And Feature.Type = catSimpleHole And Feature.ThreadingMode = catSmoothHoleThreading Then
                   
                   'Retrieve the manufacturingview

                        Set MfgView = Setup1.GetManufacturingView

        'Create a Machining Pattern

                        Set Features = MfgView.ManufacturingFeatures
                        Set ManPattern = Features.Add("MfgPatternUsage")
				if paraTole1.value = "" then
                        	ManPattern.Name = "Holes" & "_" & "Diam" & Feature.Diameter.Value & " _" & "Blind" & "_" & "Simple"
				else
                        	ManPattern.Name = "Holes" & "_" & "Diam" & Feature.Diameter.Value & " _" & "Blind" & "_" & "Simple"&"_"&paraTole1.Value
				end if	

                        MyPattern = "Holes" & "_" & "Diam" & Feature.Diameter.Value & " _" & "Blind" & "_" & "Simple"&"_"&paraTole1.Value
            		

                        For l = 1 To Shapes1.Count
                            Set oHole = Shapes1.Item(l)
                            On Error Resume Next
                            GetHoleInParameters oHole, sCommentHoleType
                            If Err <> 0 Then
                                Set oPattern = Shapes1.Item(l)

					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next

                                oPattern.ItemToCopy.GetDirection dDirArray2
                                On Error Resume Next
                                GetPatternInParameters oPattern
                                If Err <> 0 Then
                                    On Error GoTo 0
                                Else
                                    If paraTole1.Value = paraTole3.value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                            GetHoleInParameters oPattern.ItemToCopy, sCommentHoleType
                                            If Err <> 0 Then
                                                If Feature.Diameter.Value = oPattern.ItemToCopy.ItemToCopy.Diameter.Value Then
                                                    On Error Resume Next
                                                    GetHoleInParameters oPattern.ItemToCopy.ItemToCopy, sCommentHoleType
                                                        If Err <> 0 Then
                                                            On Error GoTo 0
                                                        Else
                                                            ManPattern.AddPosition oPattern, Prod, 0
                                                        End If
                                                End If
                                            Else
                                               ManPattern.AddPosition oPattern, Prod, 0
                                            End If
                                    End If
                                End If
                            Else
                                oHole.GetDirection dDirArray3
						For para3=1 to parameters.count
							if parameters.Item(para3).name = part1.Name&"\Tolerance_"&Shapes1.Item(l).Name And ok3 = False Then
								set paraTole3 = parameters1.Item(part1.Name&"\Tolerance_"&Shapes1.Item(l).Name)
								ok3 = True
							else
								ok3 = False
							end if
						Next

                                If paraTole1.Value = paraTole3.value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                     If oHole.BottomType = catFlatHoleBottom Then
                                        BottomTyp = "FlatBottom"
                                    Else: BottomTyp = "VBottom"
                                    End If
                                   ' oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Simple" & ";" & "Not Threaded" & ";" & "Blind" & ";" & BottomTyp & ";" & MyPattern
                                End If
                            End If
                        Next

'________________________________________________________________Blind Tapered

                    ElseIf c = 1 And Feature.BottomLimit.LimitMode = catOffsetLimit And Feature.Type = catTaperedHole And Feature.ThreadingMode = catSmoothHoleThreading Then
                        'Retrieve the manufacturingview
                        Set MfgView = Setup1.GetManufacturingView
                        Set Features = MfgView.ManufacturingFeatures
                        Set ManPattern = Features.Add("MfgPatternUsage")
                        ManPattern.Name = "Holes" & " _" & "Diam" & Feature.Diameter.Value & "_" & "Blind" & "_" & "Tapered"
                        MyPattern = "Holes" & " _" & "Diam" & Feature.Diameter.Value & "_" & "Blind" & "_" & "Tapered"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next

                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                                       ' oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Tapered" & ";" & "Not Threaded" & ";" & "Blind" & ";" & BottomTyp & ";" & MyPattern
                                End If
                            End If
                        Next

'________________________________________________________________blind tapered threaded

                    ElseIf c = 1 And Feature.BottomLimit.LimitMode = catOffsetLimit And Feature.Type = catTaperedHole And Feature.ThreadingMode = catThreadedHoleThreading Then
                        'Retrieve the manufacturingview
                        Set MfgView = Setup1.GetManufacturingView
                        Set Features = MfgView.ManufacturingFeatures
                        Set ManPattern = Features.Add("MfgPatternUsage")
                        ManPattern.Name = "Holes" & "_" & "Diam" & Feature.Diameter.Value & "_" & "Blind" & "_" & "Threaded" & "_" & "Tapered"
                        MyPattern = "Holes" & "_" & "Diam" & Feature.Diameter.Value & "_" & "Blind" & "_" & "Threaded" & "_" & "Tapered"
                        For l = 1 To Shapes1.Count
                            'Dim oHole As Hole
                            Set oHole = Shapes1.Item(l)
                            On Error Resume Next
                    
                            GetHoleInParameters oHole, sCommentHoleType
                            If Err <> 0 Then
                                'Dim oPattern As Pattern
                                Set oPattern = Shapes1.Item(l)
                                oPattern.ItemToCopy.GetDirection dDirArray2
                                On Error Resume Next

                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                            'Msgbox oPattern.Name
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    'Msgbox "ok2"
                                    ManPattern.AddPosition oHole, Prod, 0
                                    oHole.GetOrigin Coordarray
                                    If oHole.BottomType = catFlatHoleBottom Then
                                        BottomTyp = "FlatBottom"
                                    Else: BottomTyp = "VBottom"
                                    End If
 '                                   oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Tapered" & ";" & "Threaded" & ";" & "Blind" & ";" & BottomTyp & ";" & MyPattern
                                End If
                            End If
                        Next


  '_________________________________________________________________blind counterbored

                    ElseIf c = 1 And Feature.BottomLimit.LimitMode = catOffsetLimit And Feature.Type = catCounterboredHole And Feature.ThreadingMode = catSmoothHoleThreading Then
                        'Retrieve the manufacturingview
                        Set MfgView = Setup1.GetManufacturingView
                        'Dim Features As ManufacturingFeatures
                        Set Features = MfgView.ManufacturingFeatures
                        'Dim ManPattern As ManufacturingPattern
                        Set ManPattern = Features.Add("MfgPatternUsage")
				if paraTole1.value = "" then
                        	ManPattern.Name = "Holes" & "_" & "Diam" & Feature.Diameter.Value & " _" & "Blind" & "_" & "CounterBored"
				else
                        	ManPattern.Name = "Holes" & "_" & "Diam" & Feature.Diameter.Value & " _" & "Blind" & "_" & "CounterBored"&"_"&paraTole1.Value
				end if	
                        MyPattern = "Holes" & "_" & "Diam" & Feature.Diameter.Value & " _" & "Blind" & "_" & "Counterbored"&"_"&paraTole1.value
                        For l = 1 To Shapes1.Count
                            'Dim oHole As Hole
                            Set oHole = Shapes1.Item(l)
                            On Error Resume Next
                            GetHoleInParameters oHole, sCommentHoleType
                            If Err <> 0 Then
                                'Dim oPattern As Pattern
                                Set oPattern = Shapes1.Item(l)
					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next

                                oPattern.ItemToCopy.GetDirection dDirArray2
                                On Error Resume Next
                                GetPatternInParameters oPattern
                                If Err <> 0 Then
                                    On Error GoTo 0
                                Else
                                   If paraTole1.value = paraTole3.value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                            GetHoleInParameters oPattern.ItemToCopy, sCommentHoleType
                                            If Err <> 0 Then
                                                If Feature.Diameter.Value = oPattern.ItemToCopy.ItemToCopy.Diameter.Value Then
                                                    On Error Resume Next
                                                    GetHoleInParameters oPattern.ItemToCopy.ItemToCopy, sCommentHoleType
                                                    If Err <> 0 Then
                                                        On Error GoTo 0
                                                    Else
                                                        ManPattern.AddPosition oPattern, Prod, 0
                                                    End If
                                                End If
                                            Else
                                                ManPattern.AddPosition oPattern, Prod, 0
                                            End If
                                    End If
                                End If
                            Else
                                oHole.GetDirection dDirArray3
					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next

                                If paraTole1.value = paraTole3.value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
'                                    oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Counterbored" & ";" & "Not Threaded" & ";" & "Blind" & ";" & BottomTyp & ";" & MyPattern
                                End If
                            End If
                        Next
'___________________________________________________blind Counterbored threaded


                    ElseIf c = 1 And Feature.BottomLimit.LimitMode = catOffsetLimit And Feature.Type = catCounterboredHole And Feature.ThreadingMode = catThreadedHoleThreading Then
                                'Retrieve the manufacturingview
                        Set MfgView = Setup1.GetManufacturingView
                        Set Features = MfgView.ManufacturingFeatures
                        Set ManPattern = Features.Add("MfgPatternUsage")
                        ManPattern.Name = "Holes" & "_ " & "Diam" & Feature.Diameter.Value & " " & "Blind" & "_ " & "Threaded" & "_ " & "Counterbored"
                        MyPattern = "Holes" & "_ " & "Diam" & Feature.Diameter.Value & " " & "Blind" & "_ " & "Threaded" & "_ " & "Counterbored"
                        For l = 1 To Shapes1.Count
                            Set oHole = Shapes1.Item(l)
                            On Error Resume Next
                    
                            GetHoleInParameters oHole, sCommentHoleType
                            If Err <> 0 Then
    
                                Set oPattern = Shapes1.Item(l)
                                oPattern.ItemToCopy.GetDirection dDirArray2
                                On Error Resume Next

                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                    ManPattern.AddPosition oPattern, Prod, 0
                                        End If
        
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
            
                                    ManPattern.AddPosition oHole, Prod, 0
                                    oHole.GetOrigin Coordarray
                                    If oHole.BottomType = catFlatHoleBottom Then
                                        BottomTyp = "FlatBottom"
                                    Else: BottomTyp = "VBottom"
                                    End If
 '                                   oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Counterbored" & ";" & "Threaded" & ";" & "Blind" & ";" & BottomTyp & ";" & MyPattern
                
                                End If
                            End If
                        Next
'___________________________________________________blind Countersunk

                    ElseIf c = 1 And Feature.BottomLimit.LimitMode = catOffsetLimit And Feature.Type = catCountersunkHole And Feature.ThreadingMode = catSmoothHoleThreading Then
                        Set MfgView = Setup1.GetManufacturingView
                        Set Features = MfgView.ManufacturingFeatures
                        Set ManPattern = Features.Add("MfgPatternUsage")
				if paraTole1.value = "" then
                        	ManPattern.Name = "Holes" & "_" & "Diam" & Feature.Diameter.Value & " _" & "Blind" & "_" & "CounterSunk"
				else
                        	ManPattern.Name = "Holes" & "_" & "Diam" & Feature.Diameter.Value & " _" & "Blind" & "_" & "CounterSunk"&"_"&paraTole1.Value
				end if	

                        MyPattern = "Holes" & "_ " & "Diam" & Feature.Diameter.Value & "_ " & "Blind" & "_ " & "Countersunk"&"_"&paraTole1.Value
                        For l = 1 To Shapes1.Count
                            Set oHole = Shapes1.Item(l)
                            On Error Resume Next
                            GetHoleInParameters oHole, sCommentHoleType
                            If Err <> 0 Then
                                Set oPattern = Shapes1.Item(l)
					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next

                                oPattern.ItemToCopy.GetDirection dDirArray2
                                On Error Resume Next
                                GetPatternInParameters oPattern
                                If Err <> 0 Then
                                    On Error GoTo 0
                                Else
                                    If paraTole1.value = paraTole3.value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next

                                If paraTole1.value = paraTole3.value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    'Msgbox "ok2"
                                    ManPattern.AddPosition oHole, Prod, 0
                                    oHole.GetOrigin Coordarray
                                    If oHole.BottomType = catFlatHoleBottom Then
                                        BottomTyp = "FlatBottom"
                                    Else: BottomTyp = "VBottom"
                                    End If
 '                                   oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Countersunk" & ";" & "Not Threaded" & ";" & "Blind" & ";" & BottomTyp & ";" & MyPattern
                
                                End If
                            End If
                        Next
    
            
   '___________________________________________________________blind CounterSunk Threaded

                    ElseIf c = 1 And Feature.BottomLimit.LimitMode = catOffsetLimit And Feature.Type = catCountersunkHole And Feature.ThreadingMode = catThreadedHoleThreading Then
                        Set MfgView = Setup1.GetManufacturingView
                        Set Features = MfgView.ManufacturingFeatures
                        Set ManPattern = Features.Add("MfgPatternUsage")
                        ManPattern.Name = "Holes" & "_ " & "Diam" & Feature.Diameter.Value & "_ " & "Blind" & " _" & "Threaded" & " _" & "Countersunk"
                        MyPattern = "Holes" & "_ " & "Diam" & Feature.Diameter.Value & "_ " & "Blind" & " _" & "Threaded" & " _" & "Countersunk"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
            
                                    ManPattern.AddPosition oHole, Prod, 0
                                    oHole.GetOrigin Coordarray
                                    If oHole.BottomType = catFlatHoleBottom Then
                                        BottomTyp = "FlatBottom"
                                    Else: BottomTyp = "VBottom"
                                    End If
'                                    oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Countersunk" & ";" & "Threaded" & ";" & "Blind" & ";" & BottomTyp & ";" & MyPattern
                                End If
                            End If
                        Next
'_________________________________________________________________blind Counterdrilled

                    ElseIf c = 1 And Feature.BottomLimit.LimitMode = catOffsetLimit And Feature.Type = catCounterdrilledHole And Feature.ThreadingMode = catSmoothHoleThreading Then
                        Set MfgView = Setup1.GetManufacturingView
                        Set Features = MfgView.ManufacturingFeatures
                        Set ManPattern = Features.Add("MfgPatternUsage")
				if paraTole1.value = "" then
                        	ManPattern.Name = "Holes" & "_" & "Diam" & Feature.Diameter.Value & " _" & "CounterDrilled" & "_" & "Simple"
				else
                        	ManPattern.Name = "Holes" & "_" & "Diam" & Feature.Diameter.Value & " _" & "CounterDrilled" & "_" & "Simple"&"_"&paraTole1.Value
				end if	

                        MyPattern = "Holes" & "_ " & "Diam" & Feature.Diameter.Value & " _" & "Blind" & " _" & "Counterdrilled"&"_"&paraTole1.Value
                        For l = 1 To Shapes1.Count
                            Set oHole = Shapes1.Item(l)
                            On Error Resume Next
                            GetHoleInParameters oHole, sCommentHoleType
                            If Err <> 0 Then
                                'Dim oPattern As Pattern
                                Set oPattern = Shapes1.Item(l)
					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next
                                oPattern.ItemToCopy.GetDirection dDirArray2
                                On Error Resume Next
                                GetPatternInParameters oPattern
                                If Err <> 0 Then
                                    On Error GoTo 0
                                Else
                                    If paraTole1.value = paraTole3.value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next

                                If paraTole1.value = paraTole3.value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
 '                                   oText1.writeline oHole.Name & ";" & oHole.Diameter.Value & ";" & oHole.BottomLimit.Dimension.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Counterdrilled" & ";" & " Not Threaded" & ";" & "Blind" & ";" & BottomTyp & ";" & MyPattern
                                End If
                            End If
                        Next
'_________________________________________________________blind CounterDrilled Threaded

                    ElseIf c = 1 And Feature.BottomLimit.LimitMode = catOffsetLimit And Feature.Type = catCounterdrilledHole And Feature.ThreadingMode = catThreadedHoleThreading Then
                        Set MfgView = Setup1.GetManufacturingView
                       Set Features = MfgView.ManufacturingFeatures
                        Set ManPattern = Features.Add("MfgPatternUsage")
                        ManPattern.Name = "Holes" & " _" & "Diam" & Feature.Diameter.Value & " _" & "Blind" & " _" & "Threaded" & "_ " & "Counterdrilled"
                        MyPattern = "Holes" & " _" & "Diam" & Feature.Diameter.Value & " _" & "Blind" & " _" & "Threaded" & "_ " & "Counterdrilled"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
        
                                    ManPattern.AddPosition oHole, Prod, 0
                                    oHole.GetOrigin Coordarray
                                    If oHole.BottomType = catFlatHoleBottom Then
                                        BottomTyp = "FlatBottom"
                                    Else: BottomTyp = "VBottom"
                                    End If
  '                                  oText1.writeline oHole.Name & ";" & oHole.Diameter.Value & ";" & FormatNumber(dDirArray3(2), 2) & ";" & FormatNumber(dDirArray3(1), 2) & ";" & FormatNumber(dDirArray3(0), 2) & ";" & FormatNumber(Coordarray(0), 2) & ";" & FormatNumber(Coordarray(1), 2) & ";" & FormatNumber(Coordarray(2), 2) & ";" & "Counterdrilled" & ";" & "Threaded" & ";" & "Blind" & ";" & BottomTyp & ";" & MyPattern
                
                                End If
                            End If
                        Next
 '__________________________________________________________________Through Simple threaded           
            
                    ElseIf c = 1 And Feature.Type = catSimpleHole And Feature.ThreadingMode = catThreadedHoleThreading Then
                        Set MfgView = Setup1.GetManufacturingView
                        Set Features = MfgView.ManufacturingFeatures
                        Set ManPattern = Features.Add("MfgPatternUsage")
                        ManPattern.Name = "Holes" & " _" & "Diam" & Feature.Diameter.Value & " _" & "Through" & " _" & "Threaded" & " _" & "Simple"
                        MyPattern = "Holes" & " _" & "Diam" & Feature.Diameter.Value & " _" & "Through" & " _" & "Threaded" & " _" & "Simple"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                                End If
                            End If
                        Next
'_________________________________________________Through Simple

                    ElseIf c = 1 And Feature.Type = catSimpleHole And Feature.ThreadingMode = catSmoothHoleThreading Then
                        Set MfgView = Setup1.GetManufacturingView
                        Set Features = MfgView.ManufacturingFeatures
                        Set ManPattern = Features.Add("MfgPatternUsage")
				if paraTole1.value = "" then
                        	ManPattern.Name = "Holes" & "_ " & "Diam" & Feature.Diameter.Value & " _" & "Through" & " _" & "Simple"
				else
                        	ManPattern.Name = "Holes" & "_ " & "Diam" & Feature.Diameter.Value & " _" & "Through" & " _" & "Simple"&"_"&paraTole1.Value 
				end if	

                        MyPattern = "Holes" & "_ " & "Diam" & Feature.Diameter.Value & " _" & "Through" & " _" & "Simple"&"_"&paraTole1.Value 
                        For l = 1 To Shapes1.Count
                            Set oHole = Shapes1.Item(l)
                            On Error Resume Next
                            GetHoleInParameters oHole, sCommentHoleType
                            If Err <> 0 Then
                                Set oPattern = Shapes1.Item(l)

					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					Next
                                oPattern.ItemToCopy.GetDirection dDirArray2
                                On Error Resume Next
                                GetPatternInParameters oPattern
                                If Err <> 0 Then
                                    On Error GoTo 0
                                Else
                                    If paraTole1.Value = paraTole3.Value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3

					For para3=1 to parameters.count
						if parameters.Item(para3).name = part1.Name&"\Tolerance_"&Shapes1.Item(l).Name And ok3 = False Then
							set paraTole3 = parameters1.Item(part1.Name&"\Tolerance_"&Shapes1.Item(l).Name)
							ok3 = True
						else
							ok3 = False
						end if
					
					Next
                                If paraTole1.Value = paraTole3.Value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                
                                End If
                            End If
                        Next
                        
'__________________________________________________Through Tapered

                    ElseIf c = 1 And Feature.Type = catTaperedHole And Feature.ThreadingMode = catSmoothHoleThreading Then
                        Set MfgView = Setup1.GetManufacturingView
                        Set Features = MfgView.ManufacturingFeatures
                        Set ManPattern = Features.Add("MfgPatternUsage")
                        ManPattern.Name = "Holes" & "_ " & "Diam" & Feature.Diameter.Value & " _" & "Through" & " _" & "Tapered"
                        MyPattern = "Holes" & "_ " & "Diam" & Feature.Diameter.Value & " _" & "Through" & " _" & "Tapered"
                        For l = 1 To Shapes1.Count
                            Set oHole = Shapes1.Item(l)
                            On Error Resume Next
                        
                            GetHoleInParameters oHole, sCommentHoleType
                            If Err <> 0 Then
                                Set oPattern = Shapes1.Item(l)
                                oPattern.ItemToCopy.GetDirection dDirArray2
                                On Error Resume Next

                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                    
                                End If
                            End If
                        Next
            
'___________________________________________________Through Tapered Threaded
            
                    ElseIf c = 1 And Feature.Type = catTaperedHole And Feature.ThreadingMode = catThreadedHoleThreading Then
                        Set MfgView = Setup1.GetManufacturingView
                        Set Features = MfgView.ManufacturingFeatures
                        Set ManPattern = Features.Add("MfgPatternUsage")
                        ManPattern.Name = "Holes" & "_ " & "Diam" & Feature.Diameter.Value & "_" & "Through" & "_" & "Threaded" & " _" & "Tapered"
                        MyPattern = "Holes" & "_ " & "Diam" & Feature.Diameter.Value & "_" & "Through" & "_" & "Threaded" & " _" & "Tapered"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                    
                                End If
                            End If
                        Next


'______________________________________________________Through CouneterBored

                        ElseIf c = 1 And Feature.Type = catCounterboredHole And Feature.ThreadingMode = catSmoothHoleThreading Then
                            Set MfgView = Setup1.GetManufacturingView
                            Set Features = MfgView.ManufacturingFeatures
                            Set ManPattern = Features.Add("MfgPatternUsage")
				if paraTole1.value = "" then
                        	ManPattern.Name = "Holes" & "_" & "Diam" & Feature.Diameter.Value & " _" & "Trhough" & "_" & "CounterBored"
				else
                            ManPattern.Name = "Holes" & " _" & "Diam" & Feature.Diameter.Value & "_ " & "Through" & "_ " & "CounterBored"&"_"&paraTole1.value
				end if	

                            MyPattern = "Holes" & " _" & "Diam" & Feature.Diameter.Value & "_ " & "Through" & "_ " & "Counterbored"&"_"&paraTole1.value
                            For l = 1 To Shapes1.Count
                                Set oHole = Shapes1.Item(l)
                                On Error Resume Next
                                GetHoleInParameters oHole, sCommentHoleType
                                If Err <> 0 Then
                                    Set oPattern = Shapes1.Item(l)
						For para3=1 to parameters.count
							if parameters.Item(para3).name = part1.Name&"\Tolerance_"&Shapes1.Item(l).Name And ok3 = False Then
								set paraTole3 = parameters1.Item(part1.Name&"\Tolerance_"&Shapes1.Item(l).Name)
								ok3 = True
							else
								ok3 = False
							end if
						Next

                                    oPattern.ItemToCopy.GetDirection dDirArray2
                                    On Error Resume Next
                                    GetPatternInParameters oPattern
                                    If Err <> 0 Then
                                        On Error GoTo 0
                                    Else
                                        If paraTole1.value = paraTole3.value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                            On Error Resume Next
                                            GetHoleInParameters oPattern.ItemToCopy, sCommentHoleType
                                            If Err <> 0 Then
                                                If Feature.Diameter.Value = oPattern.ItemToCopy.ItemToCopy.Diameter.Value Then
                                                    On Error Resume Next
                                                    GetHoleInParameters oPattern.ItemToCopy.ItemToCopy, sCommentHoleType
                                                    If Err <> 0 Then
                                                        On Error GoTo 0
                                                    Else
                                                        ManPattern.AddPosition oPattern, Prod, 0
                                                    End If
                                                End If
                                            Else
                                                ManPattern.AddPosition oPattern, Prod, 0
                                            End If
                                        End If
                                    End If
                                Else
                                    oHole.GetDirection dDirArray3
						For para3=1 to parameters.count
							if parameters.Item(para3).name = part1.Name&"\Tolerance_"&Shapes1.Item(l).Name And ok3 = False Then
								set paraTole3 = parameters1.Item(part1.Name&"\Tolerance_"&Shapes1.Item(l).Name)
								ok3 = True
							else
								ok3 = False
							end if
						Next

                                    If paraTole1.Value = paraTole3.value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                        ManPattern.AddPosition oHole, Prod, 0
                                        oHole.GetOrigin Coordarray
                                        If oHole.BottomType = catFlatHoleBottom Then
                                            BottomTyp = "FlatBottom"
                                        Else: BottomTyp = "VBottom"
                                        End If
                                    End If
                                End If
                        Next
'______________________________________________________Through CounterBored Threaded

                    ElseIf c = 1 And Feature.Type = catCounterboredHole And Feature.ThreadingMode = catThreadedHoleThreading Then
                        Set MfgView = Setup1.GetManufacturingView
                        Set Features = MfgView.ManufacturingFeatures
                        Set ManPattern = Features.Add("MfgPatternUsage")
                        ManPattern.Name = "Holes" & "_" & "Diam" & Feature.Diameter.Value & "_" & "Through" & "_" & "Threaded" & "_" & "Counterbored"
                        MyPattern = "Holes" & "_" & "Diam" & Feature.Diameter.Value & "_" & "Through" & "_" & "Threaded" & "_" & "Counterbored"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                    
                                End If
                            End If
                        Next
 '________________________________________________Through CounterSunk           
            
                    ElseIf c = 1 And Feature.Type = catCountersunkHole And Feature.ThreadingMode = catSmoothHoleThreading Then
                        Set MfgView = Setup1.GetManufacturingView
                        Set Features = MfgView.ManufacturingFeatures
                        Set ManPattern = Features.Add("MfgPatternUsage")
				if paraTole1.value = "" then
                        	ManPattern.Name = "Holes" & "_" & "Diam" & Feature.Diameter.Value & " _" & "Trhough" & "_" & "CounterSunk"
				else
                            ManPattern.Name = "Holes" & " _" & "Diam" & Feature.Diameter.Value & "_ " & "Through" & "_ " & "CounterSunk"&"_"&paraTole1.value
				end if	

                        MyPattern = "Holes" & "_" & "Diam" & Feature.Diameter.Value & "_" & "Through" & " _" & "Countersunk"&"_"&paraTole1.Value
                        For l = 1 To Shapes1.Count
                            Set oHole = Shapes1.Item(l)
                            On Error Resume Next
                            GetHoleInParameters oHole, sCommentHoleType
                            If Err <> 0 Then
                                Set oPattern = Shapes1.Item(l)
						For para3=1 to parameters.count
							if parameters.Item(para3).name = part1.Name&"\Tolerance_"&Shapes1.Item(l).Name And ok3 = False Then
								set paraTole3 = parameters1.Item(part1.Name&"\Tolerance_"&Shapes1.Item(l).Name)
								ok3 = True
							else
								ok3 = False
							end if
						Next

                                oPattern.ItemToCopy.GetDirection dDirArray2
                                On Error Resume Next
                                GetPatternInParameters oPattern
                                If Err <> 0 Then
                                    On Error GoTo 0
                                Else
                                    If paraTole1.value = paraTole3.value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
						For para3=1 to parameters.count
							if parameters.Item(para3).name = part1.Name&"\Tolerance_"&Shapes1.Item(l).Name And ok3 = False Then
								set paraTole3 = parameters1.Item(part1.Name&"\Tolerance_"&Shapes1.Item(l).Name)
								ok3 = True
							else
								ok3 = False
							end if
						Next

                                If paraTole1.Value = paraTole3.value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                                End If
                            End If
                        Next
'_________________________________________________Through CounterSunk Threaded

                    ElseIf c = 1 And Feature.Type = catCountersunkHole And Feature.ThreadingMode = catThreadedHoleThreading Then
                        Set MfgView = Setup1.GetManufacturingView
                        Set Features = MfgView.ManufacturingFeatures
                        Set ManPattern = Features.Add("MfgPatternUsage")
                        ManPattern.Name = "Holes" & "_" & "Diam" & Feature.Diameter.Value & "_" & "Through" & "_" & "Threaded" & "_" & "Countersunk"
                        MyPattern = "Holes" & "_" & "Diam" & Feature.Diameter.Value & "_" & "Through" & "_" & "Threaded" & "_" & "Countersunk"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                        If oHole.BottomType = catFlatHoleBottom Then
                                            BottomTyp = "FlatBottom"
                                        Else: BottomTyp = "VBottom"
                                        End If
                    
                                End If
                            End If
                        Next

'__________________________________________________Through CounterDrilled

                    ElseIf c = 1 And Feature.Type = catCounterdrilledHole And Feature.ThreadingMode = catSmoothHoleThreading Then
                        Set MfgView = Setup1.GetManufacturingView
                        Set Features = MfgView.ManufacturingFeatures
                        Set ManPattern = Features.Add("MfgPatternUsage")
				if paraTole1.value = "" then
                        	ManPattern.Name = "Holes" & "_" & "Diam" & Feature.Diameter.Value & " _" & "Trhough" & "_" & "CounterDrilled"
				else
                            ManPattern.Name = "Holes" & " _" & "Diam" & Feature.Diameter.Value & "_ " & "Through" & "_ " & "CounterDrilled"&"_"&paraTole1.value
				end if	

                        MyPattern = "Holes" & " " & "Diam" & Feature.Diameter.Value & "_" & "Through" & "_ " & "Counterdrilled"&"_"&paraTole1.Value
                        For l = 1 To Shapes1.Count
                            Set oHole = Shapes1.Item(l)
                            On Error Resume Next
                        
                            GetHoleInParameters oHole, sCommentHoleType
                            If Err <> 0 Then
                                Set oPattern = Shapes1.Item(l)
						For para3=1 to parameters.count
							if parameters.Item(para3).name = part1.Name&"\Tolerance_"&Shapes1.Item(l).Name And ok3 = False Then
								set paraTole3 = parameters1.Item(part1.Name&"\Tolerance_"&Shapes1.Item(l).Name)
								ok3 = True
							else
								ok3 = False
							end if
						Next

                                oPattern.ItemToCopy.GetDirection dDirArray2
                                On Error Resume Next

                                GetPatternInParameters oPattern
                                If Err <> 0 Then
                                    On Error GoTo 0
                                Else
                                    If paraTole1.value = paraTole3.value And Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                    End If
                                End If
                            End If
                        Else
                            oHole.GetDirection dDirArray3
						For para3=1 to parameters.count
							if parameters.Item(para3).name = part1.Name&"\Tolerance_"&Shapes1.Item(l).Name And ok3 = False Then
								set paraTole3 = parameters1.Item(part1.Name&"\Tolerance_"&Shapes1.Item(l).Name)
								ok3 = True
							else
								ok3 = False
							end if
						Next

                            If paraTole1.value = paraTole3.Value And Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                ManPattern.AddPosition oHole, Prod, 0
                                oHole.GetOrigin Coordarray
                                If oHole.BottomType = catFlatHoleBottom Then
                                    BottomTyp = "FlatBottom"
                                Else: BottomTyp = "VBottom"
                                End If
                
                            End If
                        End If
                    Next

'____________________________________________________Through CounterDrilled Threaded

                    ElseIf c = 1 And Feature.Type = catCounterdrilledHole And Feature.ThreadingMode = catThreadedHoleThreading Then
                        Set MfgView = Setup1.GetManufacturingView
                        Set Features = MfgView.ManufacturingFeatures
                        Set ManPattern = Features.Add("MfgPatternUsage")
                        ManPattern.Name = "Holes" & "_" & "Diam" & Feature.Diameter.Value & "_" & "Through" & "_" & "Threaded" & "_" & "Counterdrilled"
                        MyPattern = "Holes" & "_" & "Diam" & Feature.Diameter.Value & "_" & "Through" & "_" & "Threaded" & "_" & "Counterdrilled"
                        For l = 1 To Shapes1.Count
                            Set oHole = Shapes1.Item(l)
                            On Error Resume Next
                            GetHoleInParameters oHole, sCommentHoleType
                            If Err <> 0 Then
                                Set oPattern = Shapes1.Item(l)
                                oPattern.ItemToCopy.GetDirection dDirArray2
                                On Error Resume Next
                                GetPatternInParameters oPattern
                                If Err <> 0 Then
                                    On Error GoTo 0
                                Else
                                    If Feature.Diameter.Value = oPattern.ItemToCopy.Diameter.Value And FormatNumber(dDirArray2(2), 2) = FormatNumber(dDirArray(2), 2) And FormatNumber(dDirArray2(1), 2) = FormatNumber(dDirArray(1), 2) And FormatNumber(dDirArray2(0), 2) = FormatNumber(dDirArray(0), 2) And oPattern.ItemToCopy.BottomLimit.LimitMode = Feature.BottomLimit.LimitMode And oPattern.ItemToCopy.ThreadingMode = Feature.ThreadingMode And oPattern.ItemToCopy.Type = Feature.Type Then
                                        On Error Resume Next
                                        GetHoleInParameters oPattern.ItemToCopy, sCommentHoleType
                                        If Err <> 0 Then
                                            If Feature.Diameter.Value = oPattern.ItemToCopy.ItemToCopy.Diameter.Value Then
                                                On Error Resume Next
                                                GetHoleInParameters oPattern.ItemToCopy.ItemToCopy, sCommentHoleType
                                                If Err <> 0 Then
                                                    On Error GoTo 0
                                                Else
                                                    ManPattern.AddPosition oPattern, Prod, 0
                                                End If
                                            End If
                                        Else
                                            ManPattern.AddPosition oPattern, Prod, 0
                                        End If
                                    End If
                                End If
                            Else
                                oHole.GetDirection dDirArray3
                                If Feature.Diameter.Value = oHole.Diameter.Value And FormatNumber(dDirArray3(2), 2) = FormatNumber(dDirArray(2), 2) And FormatNumber(dDirArray3(1), 2) = FormatNumber(dDirArray(1), 2) And FormatNumber(dDirArray3(0), 2) = FormatNumber(dDirArray(0), 2) And oHole.BottomLimit.LimitMode = Feature.BottomLimit.LimitMode And Feature.Type = oHole.Type And Feature.ThreadingMode = oHole.ThreadingMode Then
                                    ManPattern.AddPosition oHole, Prod, 0
                                    oHole.GetOrigin Coordarray
                                    If oHole.BottomType = catFlatHoleBottom Then
                                        BottomTyp = "FlatBottom"
                                    Else: BottomTyp = "VBottom"
                                    End If
                                End If
                            End If
                        Next
            
                    End If
                End If
        Next

'Modifying the jumpDistance of the Machining Pattern

Dim Jump As Parameter
Set Jump = ManPattern.GetAnAttribute("JumpDistance")

Jump.ValuateFromString ("50mm")

' Added by cvr to manage ODT
If RemoveBox = "" Then
	MsgBox "Machining Patterns created"
End If





    Else: MyString2 = "No"
    End If

' Added by cvr to manage ODT
If RemoveBox = "" Then
	MsgBox "End"
End If

End Sub


'**********************************************************************************************
'Purpose : retrieve the characteristics of Pattern
'
'**********************************************************************************************

Sub GetPatternInParameters(oPattern)


Dim globAng As Angle
Set globAng = oPattern.RotationAngle

End Sub
'****************************************************************************************************
'Create Pattern
'************************************************************************************************


' ******************************************************************************************
' Purpose:  retrieve the characteristics of Hole feature
'
' Inputs:   oHole:          the hole feature
'       dPlateThickness:    Thickness of the plate (depends on the part and
'                   its creation)
'
' ******************************************************************************************

Sub GetHoleInParameters(oHole, sCommentHoleType)
    
    If oHole.Type = catSimpleHole Then
        sCommentHoleType = "Simple"
    ElseIf oHole.Type = catTaperedHole Then
        sCommentHoleType = "Tapered"
    ElseIf oHole.Type = catCounterboredHole Then
        sCommentHoleType = "Counterbored"
    ElseIf oHole.Type = catCountersunkHole Then
        sCommentHoleType = "Countersunk"
    Else
        sCommentHoleType = "Counterdrilled"
    End If
        
End Sub
