Language="VBSCRIPT"

Sub CATMain()

'---  Input a list of components
'--- it must contains lines with the path of the components
'-- example
'E:\NOBACKUP\DownloadOfCXR20Rel\intel_a\startup\components\MoldCatalog\CapScrew\Dme\CapScrew_Is610\CapScrew_Is610.CATPart
'---  This macro is intended to create as many CATParts as there are line in the DT
'--- the DT is removed from the component
'--- the name if the new component is suffixed by the KW parameter REF
'--- the nomenclature property is set with the KW parameter REF
'--- the KW parameters driven by the DT are hidden
'       for the list of components given as input.
'xxxxxxxxxxxxxxx You must allow enough space !xxxxxxxxxxxxxxxxxxxxxxx
'xxxxxxxxxxxxxxx This does not handle the components using KW parameter REFBOM xxxxxxxxxxxxx
'---  Some directories and names must be defined in the first lines of the macro
'**********************************************************************
'------------------------------------------------------------------------------------
' ------------------------------------------------------------------------------
' ------------------------------------------------------------------------------
' ------------------------------------------------------------------------------

' Sample of commands to launch in a command prompt to get the path and name of components in a txt file 
'find E:\MyDir\startup\components\MoldCatalog\Sleeve\Dme\ -name "*.CATPart" |sed -e "s/\//\\/g">ListOfCmp.txt
'
' or else :
' in run : cmd  ( to get a command window )
' in this window : E: ( to be positionned in appropriate drive )
' in this window : cd NoBackup\downloadOfCXR20Rel\intel_a\startup\components\MoldCatalog  ( to be postionned in right directory )
' in this window : dir /s /B  *.CATPart > MyListOfComponents.txt
'------------------------------------------------------------------------------------
' ------------------------------------------------------------------------------
' ------------------------------------------------------------------------------
' ------------------------------------------------------------------------------
'**********************************************************************

'**********************************************************************
'------------------------------------------------------------------------------------
' ------------------------------------------------------------------------------
' ------------------------------------------------------------------------------
' ------------------------------------------------------------------------------
' Please, the following path of files can be modified to meet your requirements.


' this is the path of directory where the list of components will be found 
    FromDir = "E:\MyFolder\Input\"
' this is the path of the directory where the output files will be created
    WhereDir =  "E:\MyFolder\Output\"
' this is the path of the directory where the new CATPart files will be created
    ResolvedDir =  "E:\MyFolder\Resolved\"

' this is the name of the list of components ( a txt file containing all the component path, one per line, no suffix )
    ListOfComponents = "MyListofComponents"
' this is the name of the report file
    ReportFileName = "MyResolvedComponentsList"        '   ( no suffix )



'------------------------------------------------------------------------------------
' ------------------------------------------------------------------------------
' ------------------------------------------------------------------------------
' ------------------------------------------------------------------------------
'**********************************************************************
err.clear

	Dim COLORBGHTML As String, COLORTXTHTML As String
	Dim LANCEMENT_EN_BATCH As String
	LANCEMENT_EN_BATCH  = CATIA.SystemService.Environ("RUN_BATCH")

	COLORBGHTML=WHITE
	COLORTXTHTML=BLACK

'**********************************************************************
	ListOfCmpFile = FromDir&ListOfComponents&".txt"	' for the input file
	ReportFile = WhereDir&ReportFileName&".txt"   '  for report file


' ListOfCmp.txt = file that contains the path of all components (CATPart) to test
' -------------------------------------------------------------------------------
Dim filesys, MyCmp
Set filesys = CreateObject("Scripting.FileSystemObject") 
on error resume next
Set MyCmp = filesys.OpenTextFile(ListOfCmpFile)
If (Err <> 0) Then
	Msg = "The file: " &ListOfCmpFile  & " of components to test does not exist"
	MsgBox Msg
	On Error Goto 0
Else

' ReportIndexFile.txt = File that contains all the files read
' -------------------------------------------------------------------------------------------------------------------
	Dim filesysIF, textIF
	Set filesysIF = CreateObject("Scripting.FileSystemObject") 

' ReportNoFile.txt = File that contains the results of the files not found
' -------------------------------------------------------------------------------------------------------------------
	Dim filesysNF, textNF
	Set filesysNF = CreateObject("Scripting.FileSystemObject") 

' ReportFileName.txt = file that contains the report
' -------------------------------------------------------------------------------------------------------------------
	Dim filesysRP, textRP
	Set filesysRP = CreateObject("Scripting.FileSystemObject") 

'------------------------------------------------------------------------------------------------------------------------
'------------------------------------------------------------------------------------------------------------------------
'------------------------------------------------------------------------------------------------------------------------
'------------------------------------------------------------------------------------------------------------------------
'------------------------------------------------------------------------------------------------------------------------
'------------------------------------------------------------------------------------------------------------------------
'------------------------------------------------------------------------------------------------------------------------------------------------
	Dim encore, wego
	encore = true
	wego = true
    tstrp = false

' Ask to analyze ?
' ------------------------------
    Msgbox "Make sure the Tools/option -no automatic back up- is -ON-"
	Message = "Would you like to resolve the components ?"&"It is recommanded to create the Technological Results before resolution"
	Style = vbYesNo + vbDefaultButton2    'Define buttons.
	Title = "Resolving Tooling Components"
	Response = MsgBox(Message, Style, Title)
	If Response = vbYes Then
        tstRP= true
	End If

	if ( tstrp  ) then  Set textRP = filesys.CreateTextFile(ReportFile , True)


'--------------end of dialog -------------------------------------------

	If (not tstrp) then
		MsgBox "Sorry there are no other option available !!!"
		wego = false
	else

' The tests start !!!
        NBcmp=0
		do while (encore)

'            Checking if this is the last component
			CmpRead = MyCmp.AtEndOfStream
			if (CmpRead) then
'				MsgBox "End"
				encore = false
			else
'				MsgBox "Go on"
'               Reading the next component
				CmpRead = MyCmp.ReadLine
                Nbcmp=Nbcmp+1
'               Opening it
				Set documents1 = CATIA.Documents
				tstNF = true
                on error resume next
				Set partDocument1 = documents1.Open(CmpRead)
				If (Err <> 0) Then
                    msgbox "The file: " &CmpRead  & " does not exist"
					tstNF = false
                    err.clear
                else

'               The component is good
'				MsgBox "Current line = " &CmpRead
				if (tstRP) then
'					textRP.WriteLine Nbcmp &" Component: " & CmpRead
					ProcessComponents  textRP, CmpRead ,  ResolvedDir 
				end if
	            PartDocument1.Close
				end if
			end if
		loop
	end if


	if (tstRP) then textRP.Close

	if (wego) then MsgBox "We hope you enjoy the results !!!"
End If

End Sub

'----------------------------------------------------------------------------------------
' Sub to resolve the DT
'----------------------------------------------------------------------------------------

   Sub ProcessComponents ( text, CmpFile, ResolvedDir )


   NbPbEncountered = 0

'-- identification of the DesignTable
   err.clear
   On Error goto 0
    Set partDocument1 = CATIA.ActiveDocument
	Dim part1 As Part
	Set part1 = partDocument1.Part
	Partname=Part1.name




' nb de caracters du Partname
       nbcharF=1
       For I =1 to 1000
       if ( Right (Partname,nbcharF)<>Partname ) then
            nbcharF=nbcharF+1
       else
             I=2000           
       end if
       next


'--- extraction of the useful part
'--- recherche du "_"
          ShortName="Not Set"
     for NBchar=1 to NbCharF
          TryName= Left (PartName,NBChar)
          ILast= Right (TryName,1)
          if ( Ilast="_" ) then
                      ShortName= Left (PartName,NBChar-1)
                      NBChar=NbCharF+1
          end if
      next
      if (ShortName="Not Set") then
            ShortName= PartName
      end if

	
' Search the design table via the parameter named Ref
	Dim relations1 As Relations
	Set relations1 = part1.Relations
	Dim parameters1 As Parameters
	Set parameters1 = part1.Parameters
	Dim RefParam As Parameter
	Set RefParam = parameters1.Item("Ref")
	RefName = RefParam.Name
	'text.writeline "param name =  " &RefName
	Dim relation0 As Relation
	set relation0 = RefParam.OptionalRelation
'	text.writeline "Name of design table =  " &relation0.Name
	Set designTable1 = relations1.Item(relation0.name)

	If (Err <> 0) Then
'		text.WriteLine "<B><FONT COLOR=RED> Design Table " & relation0.name & " not found </B></FONT>"
		NbPbEncountered = NbPbEncountered + 1
    else

	NbConfig = designTable1.ConfigurationsNb
    NbColumns = designTable1.ColumnsNb
	If (NbConfig < 0) Then NbPbEncountered = 1

	'MsgBox("Nombre de configurations = " & NbConfig)
'	text.WriteLine "---> Number of configurations to export " & NbConfig
    dim partnames(10000)
 	For I = 1 to NbConfig

		err.clear
		On Error Resume Next
		designTable1.Configuration = I
		part1.Update
		If (Err <> 0) Then
'			MsgBox("Problem update configuration = " & I)
			text.WriteLine "<B><FONT COLOR=RED> Update problem for configuration " & I & "</B></FONT>"
			NbPbEncountered = NbPbEncountered + 1
        else
             Isuffix="_"& refparam.valueasstring
			 Set partDocument2 = documents1.Open(ResolvedDir&ShortName&Isuffix&".CATPart")
             partnames(I)=  ResolvedDir&ShortName&Isuffix&".CATPart"
             partDocument1.SaveAs ResolvedDir&ShortName&Isuffix&".CATPart"
             err.clear
	    	text.WriteLine ResolvedDir&ShortName&Isuffix&".CATPart"
		End If
	Next


end if



if (NbPbEncountered > 0) then
'	text.WriteLine "<B><FONT COLOR=RED> ---> Number of problems found " & NbPbEncountered  & "</B></FONT>"
else
'	text.WriteLine "---> No problem found"
end if
'text.WriteLine " "

End Sub
