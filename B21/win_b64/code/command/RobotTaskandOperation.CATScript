'// ---------- CATIAV5 application objects

'====================================================================================
Sub CATMain () 'Method to Work around with RobotTask/Operation/RobotMotion
'************************************************************************************
'->Insert the Robot IRB_1400 into the Process Doc.
'->Create a Tag Group with 7 Tags
'->Create a Robot task(RobotTask.1) and add the  TagGroup To the Created Robot Task
'->For the RobotMotion/Opeartion6/RobotTask.1 set turn numbers as 2,3,4,5
'->For the robot Task Create a Retract and a 
'  weld action after Robot Motion 1 in Operation 2
'*The CATScript then does the following
'  *Creates 3 Robot Tasks with names New_RobotTask_1,New_RobotTask_2,New_RobotTask_3
'  *Creates 3 operations in each New_RobotTask_1 and New_RobotTask_2
'  *Creates a RobotMotion for a New_RobotTask_1/Operation1
'  *The Operation 1 of the RobotTask.1 is set to Via Mode
'  *The MotionType of Operation 1is set to LinearMove
'  *The RobotMotion/Operation 3  is Set with a new cartesian target
'  *The RobotMotion/Operation 1/ New_RobotTask_1is set with Tag Target of RobotMotion/Operation 2/RobotTask.1
'  *The RobotMotion/Operation 4 is set with Tag Target of RobotMotion/Operation 2
'  *The RobotMotion/Operation5 is set with a joint Target
'  *The RobotMotion/Operation7 is set with Turn Number values of RobotMotion/Operation6
'  *RobotMotion/Operation6 is set with config3
'  *Calltask of  RobotTask.1 in New_RobotTask_1 in after operation 2 is created
'  *All operations of New_RobotTask_2 are deleted
'  *New_RobotTask_3 is deleted
'
'====================================================================================
Dim processDoc as PPRDocument
set processDoc = CATIA.ActiveDocument.PPRDocument

Dim rsrcs as Products
set rsrcs = processDoc.Resources


Dim count
Dim name as String
Dim objProduct As Product
Dim objRobot As Product
Dim objRobotTaskFactory as RobotTaskFactory
Dim objRobotTask(3) as RobotTask
Dim objOperation1(7) as Operation
Dim objOperation2(2) as Operation  
Dim objOperation3(2) as Operation 
Dim objRobotmotion as RobotMotion
count=rsrcs.Count

for i=1 to count
Set objProduct  = rsrcs.Item(i)
name= objProduct.Name
if(name="IRB_1400.1") then
   Set objRobot=objProduct
end If
next 

Set objProduct = Nothing
Set objRobotTaskFactory = objRobot.GetTechnologicalObject("RobotTaskFactory" )
Set objRobot = Nothing

msgbox("Creating 3 more Robottasks")
objRobotTaskFactory.CreateRobotTask "New_RobotTask_1",objRobotTask(1)
objRobotTaskFactory.CreateRobotTask "New_RobotTask_2",objRobotTask(2)
objRobotTaskFactory.CreateRobotTask "New_RobotTask_3",objRobotTask(3) 

msgbox("Now the RobotTasks created in the document are")
objRobotTaskFactory.GetAllRobotTasks objRobotTask
for k=0 to 3 step 1
name=objRobotTask(k).Name
msgbox(name)
next

msgbox("The operations in RobotTask.1 are")
objRobotTask(0).GetAllOperations objOperation1
for k=0 to 6 step 1
name=objOperation1(k).Name
msgbox(name)
next

msgbox("Creating 3 operations in New_RobotTask_1")
Dim objOpr as Operation
Set objOpr = Nothing
objRobotTask(1).CreateOperation objOpr,objOpr,objOperation2(0)
objOperation2(0).CreateRobotMotion objOpr,TRUE,objRobotmotion
objRobotTask(1).CreateAfterOperation objOperation2(0),objOperation2(1)
objRobotTask(1).CreateAfterOperation objOperation2(1),objOperation2(2)

msgbox("The operations in New_RobotTask_1 are")
objRobotTask(1).GetAllOperations objOperation2
for k=0 to 2 step 1
name=objOperation2(k).Name
msgbox(name)
next

msgbox("Creating 3 operations in New_RobotTask_2")
objRobotTask(2).CreateOperation objOpr,objOpr,objOperation3(0)
objRobotTask(2).CreateAfterOperation objOperation3(0),objOperation3(1)
objRobotTask(2).CreateAfterOperation objOperation3(1),objOperation3(2)

Set objOpr = Nothing

msgbox("The operations in New_RobotTask_2 are")
objRobotTask(2).GetAllOperations objOperation3
for k=0 to 2 step 1
name=objOperation3(k).Name
msgbox(name)
next

Dim ActionList(2)
msgbox("The actions of Operation.1 of the RobotTask.1 are")
objOperation1(0).GetActions ActionList
for k=0 to 1 
name=ActionList(k).Name
msgbox(name)
next

msgbox("Operation.1 of the RobotTask.1 is ")
Dim t
objOperation1(0).GetViaMode t
if   t=1 then
	msgbox("ViaMode")
else
	if t =0  then
		msgbox("Untyped")
	end If
end If

msgbox("Changing Operation.1 of the RobotTask.1 to ViaMode ")
objOperation1(0).SetViaMode 1

msgbox("Getting the motion type of Operation.1 of RobotTask ")
objOperation1(0).GetRobotMotion objRobotmotion
Dim s
objRobotmotion.GetMotionType s
if   s=1 then
	msgbox("Linear Move")
end If
if s =0  then
	msgbox("Joint move")
end If
if s=2  then
	msgbox("PREDEFINED")
end If
if s=3  then
	msgbox("CIRCULAR")
end If
if s=4  then
	msgbox("CIRCULARVIA")
end If

msgbox("Setting the motion type to linear Move")
objRobotmotion.SetMotionType 1
msgbox("Getting the motion type now ")
Dim r
objRobotmotion.GetMotionType r
if   r=1 then
	msgbox("Linear Move")
end If
if r=0  then
	msgbox("Joint move")
end If
if r =2  then
	msgbox("PREDEFINED")
end If
if r=3  then
	msgbox("CIRCULAR")
end If
if r =4  then
	msgbox("CIRCULARVIA")
end If

msgbox("Getting the Target type of Operation.1 of RobotTask.1 ")
objOperation1(0).GetRobotMotion objRobotmotion
Dim q
objRobotmotion.GetTargetType q
if   q=0 then
	msgbox("CARTESIANTARGET")
end If
if q=1  then
	msgbox("JOINTTARGET")
end If
if q=2  then
	msgbox("TAGTARGET")
end If
if i =3  then
	msgbox("HOMETARGET")
end If

Dim objTag as TAG

msgbox("Obtaining the Tag Taget of Operation.2 of the RobotTask.1")
objOperation1(1).GetRobotMotion objRobotmotion
objRobotmotion.GetTagTarget objTag 
msgbox("The name of the  contained tag is")
name=objTag.Name
msgbox(name)

msgbox("Setting of RobotMotion of Operation1 in New_RobotTask_1 with the Tag Taget of Operation.2 of the RobotTask.1")
Dim objRobotmotion1
objOperation2(0).GetRobotMotion objRobotmotion1 
objRobotmotion1.SetTagTarget objTag

Dim CartesianTarget(5)
CartesianTarget(0)=150
CartesianTarget(1)=200
CartesianTarget(2)=350
CartesianTarget(3)=1.571
CartesianTarget(4)=3.142
CartesianTarget(5)=-0.785
Dim CartesianTarget1(5)
msgbox("Setting the Operation.3 of the RobotTask.1 with Cartesiantarget")
objOperation1(2).GetRobotMotion objRobotmotion
objRobotmotion.SetCartesianTarget CartesianTarget

msgbox("Setting Operation.4 of the RobotTask.1 with the Tag of Operation2")
objOperation1(3).GetRobotMotion objRobotmotion
objRobotmotion.SetTagTarget objTag
msgbox("The name of the  contained tag is")
name=objTag.Name
msgbox(name)

Set objTag = Nothing

Dim JointTarget(5)
JointTarget(0)=1.571
JointTarget(1)=-0.785
JointTarget(2)=3.142
JointTarget(3)=0.38
JointTarget(4)=1.57
JointTarget(5)=0.6

Dim JointTarget1(5)
msgbox("Setting the Operation.5 of the RobotTask.1 with Jointtarget")
objOperation1(4).GetRobotMotion objRobotmotion
objRobotmotion.SetJointTarget JointTarget

Dim TurnNumbers(6)
msgbox("Gettting the turn number of Operation.6 of the RobotTask.1 ")
objOperation1(5).GetRobotMotion objRobotmotion
objRobotmotion.GetTurnNumbers TurnNumbers
msgbox("the turn numbers for this Operation are")
for j=0 to 3
msgbox(TurnNumbers(j))
next 

msgbox("Setting this as the turn number of Operation.7 of RobotTask.1")
objOperation1(6).GetRobotMotion objRobotmotion
objRobotmotion.SetTurnNumbers TurnNumbers

Dim a
msgbox("getting the Config of Operation.6 of the RobotTask.1 ")
objOperation1(6).GetRobotMotion objRobotmotion
objRobotmotion.GetConfig a
msgbox(a+1)
msgbox("Setting the cofig of Operation.6 of RobotTask.1 to Config 4")
objOperation1(6).GetRobotMotion objRobotmotion
objRobotmotion.SetConfig 3
msgbox("The set config is")
objOperation1(6).GetRobotMotion objRobotmotion
objRobotmotion.GetConfig m
msgbox(m+1)

Dim objCreatedtask as AnyObject
msgbox("Creating a call task of  RobotTask.1 in New_RobotTask_1  after operation 2")
objRobotTask(1).CreateCallTask objRobotTask(0),objOperation1(2),1,objCreatedtask

msgbox("Deleting all operations of New_RobotTask_2")
objRobotTask(2).DeleteOperations objOperation3

msgbox("Deleting the New_RobotTask_3")
objRobotTaskFactory.DeleteRobotTask objRobotTask(3)

Set objCreatedtask = Nothing
Set objRobotTaskFactory = Nothing
Set objRobotmotion = Nothing

for k=1 to 3 step 1
Set objRobotTask(k) =  Nothing
next
Set objRobotTask = Nothing

for k=1 to 7 step 1
Set objOperation1(k) =  Nothing
next
Set objOperation1 = Nothing

for k=1 to 2 step 1
Set objOperation2(k) =  Nothing
next
Set objOperation2 = Nothing

for k=1 to 2 step 1
Set objOperation3(k) =  Nothing
next
Set objOperation3 = Nothing
End Sub '/////////////////////////////////////////////////////////// CATMain
