'// ---------- CATIAV5 application objects
'====================================================================================
Sub CATMain () 'Method to mount Devices on to a Robot 
'====================================================================================
'*************************************************************************************
'* Select IRB_1400 as the Robot                                                      *
'* Devices: Mount 4 Devices and remember their sequence                              *
'*          Unmount the Third device                                                 *                         
'*************************************************************************************
Dim processDoc as PPRDocument
set processDoc = CATIA.ActiveDocument.PPRDocument

Dim rsrcs as Products
set rsrcs = processDoc.Resources

Dim objRobot as Product
Dim objProduct as Product
Dim objDevice as Product

Dim count
Dim name as String
count=rsrcs.Count

for i=1 to count
Set objProduct  = rsrcs.item(i)
name= objProduct.Name
if(name="IRB_1400.1") then
   Set objRobot=objProduct
end If
next 

Dim objMountManager as MountManager
Set objMountManager = objRobot.GetTechnologicalObject("MountManager" )
Dim DeviceList(3) as Product

objMountManager.GetMountedDevices DeviceList

msgbox("Unmounting the second Device ")
objMountManager.UnMountDevice DeviceList(1)


Dim IsMounted As Boolean
msgbox("ReMounting the Third Device")
objMountManager.ReMountDevice DeviceList(2) 

msgbox("Now checking which all devices are mounted")

for i=0 to 3
objMountManager.IsDeviceMounted DeviceList(i),IsMounted
name=DeviceList(i).Name
msgbox(name)
if IsMounted =True  then
   msgbox " is  mounted"
else
   msgbox " is not mounted"
end If
next

msgbox("Unseting the Fourth Device ")
objMountManager.UnSetDevice DeviceList(3)

msgbox("Now checking which all devices are mounted")

for i=0 to 2
objMountManager.IsDeviceMounted DeviceList(i),IsMounted
name=DeviceList(i).Name
msgbox(name)
if IsMounted =True  then
   msgbox " is  mounted"
else
   msgbox " is not mounted"
end If
next



End Sub '/////////////////////////////////////////////////////////// CATMain
