Attribute VB_Name = "Module1"
Private Declare Function GetTempPath Lib "kernel32" Alias "GetTempPathA" (ByVal nBufferLength As Long, ByVal lpBuffer As String) As Long
Sub CATMain()
On Error Resume Next
Dim objxml As DOMDocument
Dim settingControllers1 As SettingControllers
Set settingControllers1 = CATIA.SettingControllers
Set reportingSettings = settingControllers1.Item("DNBIgpFASReportingSettingCtrl")
Dim outputDir
outputDir = reportingSettings.ResultOutputDir
' Find the File Name
Dim fileDoc As Document
Set fileDoc = CATIA.ActiveDocument
Dim fileName
fileName = fileDoc.Name
Dim fname() As String
fname = Split(fileName, ".")

Set objxml = CreateObject("Microsoft.XMLDOM")
Dim outputXMLFile
outputXMLFile = outputDir & "\" & fname(0) & "\Run_1\Reporting.xml"
'MsgBox (outputXMLFile)
'objxml.Load ("d:\\temp\\reporting.xml")
objxml.Load (outputXMLFile)
Set objLst = objxml.getElementsByTagName("Resource")
Dim strCATTempPath As String
Dim TempPath As String
Dim slength As Long
TempPath = Space(255)
slength = GetTempPath(255, TempPath)
TempPath = Left(TempPath, slength)

'strCATTempPath = CATIA.SystemService.Environ("CATTemp")

strCATTempPath = outputDir & "\" & fname(0) & "\Run_1\" & "VBAXMLexample.htm"
'MsgBox (strCATTempPath)
Dim Indexfs
Set Indexfs = CreateObject("Scripting.FileSystemObject")
Set indexf = Indexfs.OpenTextFile(strCATTempPath, 2, True)


Set ActObject = CATIA.ActiveDocument.Selection.FindObject("CATIAActivity")
    ' Query a single node.
    'Dim oNode As IXMLDOMNode
    'Set oNode = objxml.selectSingleNode("//Task[@Name = '" & ActObject.Name & "']")
    Dim oNodeList As IXMLDOMNodeList
    Set oNodeList = objxml.selectNodes("//Task[@Name = '" & ActObject.Name & "']")

    'MsgBox (oNodes.Length)
 indexf.WriteLine "<!doctype html public ""-//w3c//dtd html 4.0 transitional//en"">"
  indexf.WriteLine "<html>"
  indexf.WriteLine "<head>"
  indexf.WriteLine "   <meta http-equiv=""Content-Type"" content=""text/html; charset=iso-8859-1"">"
  indexf.WriteLine "   <meta name=""GENERATOR"" content=""IPD v2"">"
  indexf.WriteLine "   <meta name=""Author"" content=""IPD v2"">"
  indexf.WriteLine "   <title>Task:" & ActObject.Name & "</title>"
  indexf.WriteLine "</head>"
  indexf.WriteLine "<body background=""back.gif"" bgcolor=#EEEEFF>"
  
  Dim sName As String
  Dim dblTotalTime As Double
  Dim nodeId As IXMLDOMAttribute
  Dim oNodes As IXMLDOMNodeList
  Dim oTaskNode As IXMLDOMNode
  
  For Idx = 0 To oNodeList.Length - 1
    Set oTaskNode = oNodeList.nextNode
    indexf.WriteLine "   <h2>Task Details: " & ActObject.Name & "     Instance : " & (Idx + 1) & "</h2>"
    indexf.WriteLine "<table border=1 width=""100%"" bordercolorlight=""#000000"" cellspacing=0 cellpadding=0>"
  indexf.WriteLine "<tr>"
  indexf.WriteLine "<td width=""20%""><b>Activity Name</b></td>"
  indexf.WriteLine "<td width=""20%""><b>Motion Time</b></td>"
  indexf.WriteLine "<td width=""20%""><b>Idle Time</b></td>"
  indexf.WriteLine "<td width=""20%""><b>Delay Time</b></td>"
  indexf.WriteLine "<td width=""20%""><b>Process CycleTime</b></td>"
  indexf.WriteLine "</tr>"
  
  'Set oNodes = oNode.childNodes
    Set oNodes = oTaskNode.childNodes
  For I = 0 To oNodes.Length - 1
  
    Set oNode = oNodes.nextNode
      If Not (oNode Is Nothing) Then
        
         sName = oNode.nodeName
         
         Select Case sName
            Case "StartTime"
                    'MsgBox (sName)
            Case "EndTime"
                    'MsgBox (sName)
            Case "Motion"
                    indexf.WriteLine "<tr>"
                    Set nodeId = oNode.Attributes.getNamedItem("Name")
                    'get the start and end values..
                    Dim oChildNodes As IXMLDOMNodeList
                    Dim oChildNodeStart As IXMLDOMNode
                    Dim oChildNodeEnd As IXMLDOMNode
                    Set oChildNodes = oNode.childNodes
                    Set oChildNodeStart = oChildNodes.Item(0)
                    Set oChildNodeEnd = oChildNodes.Item(1)
                    Dim iStart As Double
                    Dim iEnd As Double
                    iStart = Val(oChildNodeStart.Text)
                    iEnd = Val(oChildNodeEnd.Text)
                    indexf.WriteLine "<td width=""20%"" height=19>&nbsp;" & nodeId.Value & "</td>"
                    indexf.WriteLine "<td width=""20%"" height=19>" & (iEnd - iStart) & "</td>"
                    dblTotalTime = dblTotalTime + (iEnd - iStart)
                    indexf.WriteLine "<td width=""20%"" height=19>" & 0 & "</td>"
                    indexf.WriteLine "<td width=""20%"" height=19>" & 0 & "</td>"
                    indexf.WriteLine "<td width=""20%"" height=19>" & dblTotalTime & "</td>"
                    indexf.WriteLine "</tr>"
            Case "Set"
                    indexf.WriteLine "<tr>"
                    Set nodeId = oNode.Attributes.getNamedItem("Name")
                     'get the start and end values..
                    Set oChildNodes = oNode.childNodes
                    Set oChildNodeStart = oChildNodes.Item(0)
                    Set oChildNodeEnd = oChildNodes.Item(1)
                    'Dim iStart As Double
                    'Dim iEnd As Double
                    iStart = CDbl(oChildNodeStart.Text)
                    iEnd = CDbl(oChildNodeEnd.Text)
                    indexf.WriteLine "<td width=""20%"" height=19>&nbsp;" & nodeId.Value & "</td>"
                    indexf.WriteLine "<td width=""20%"" height=19>" & 0 & "</td>"
                    dblTotalTime = dblTotalTime + (iEnd - iStart)
                    indexf.WriteLine "<td width=""20%"" height=19>" & (iEnd - iStart) & "</td>"
                    indexf.WriteLine "<td width=""20%"" height=19>" & 0 & "</td>"
                    indexf.WriteLine "<td width=""20%"" height=19>" & dblTotalTime & "</td>"
                    indexf.WriteLine "</tr>"
            Case "Wait"
                    indexf.WriteLine "<tr>"
                    Set nodeId = oNode.Attributes.getNamedItem("Name")
                     'get the start and end values..
                    Set oChildNodes = oNode.childNodes
                    Set oChildNodeStart = oChildNodes.Item(0)
                    Set oChildNodeEnd = oChildNodes.Item(1)
                    'Dim iStart As Double
                    'Dim iEnd As Double
                    iStart = CDbl(oChildNodeStart.Text)
                    iEnd = CDbl(oChildNodeEnd.Text)
                    indexf.WriteLine "<td width=""20%"" height=19>&nbsp;" & nodeId.Value & "</td>"
                    indexf.WriteLine "<td width=""20%"" height=19>" & 0 & "</td>"
                    dblTotalTime = dblTotalTime + (iEnd - iStart)
                    indexf.WriteLine "<td width=""20%"" height=19>" & (iEnd - iStart) & "</td>"
                    indexf.WriteLine "<td width=""20%"" height=19>" & 0 & "</td>"
                    indexf.WriteLine "<td width=""20%"" height=19>" & dblTotalTime & "</td>"
                    indexf.WriteLine "</tr>"
            Case "Delay"
                    indexf.WriteLine "<tr>"
                    Set nodeId = oNode.Attributes.getNamedItem("Name")
                    'get the start and end values..
                    Set oChildNodes = oNode.childNodes
                    Set oChildNodeStart = oChildNodes.Item(0)
                    Set oChildNodeEnd = oChildNodes.Item(1)
                    iStart = CDbl(oChildNodeStart.Text)
                    iEnd = CDbl(oChildNodeEnd.Text)
                    indexf.WriteLine "<td width=""20%"" height=19>&nbsp;" & nodeId.Value & "</td>"
                    indexf.WriteLine "<td width=""20%"" height=19>" & 0 & "</td>"
                    dblTotalTime = dblTotalTime + (iEnd - iStart)
                    indexf.WriteLine "<td width=""20%"" height=19>" & 0 & "</td>"
                    indexf.WriteLine "<td width=""20%"" height=19>" & (iEnd - iStart) & "</td>"
                    indexf.WriteLine "<td width=""20%"" height=19>" & dblTotalTime & "</td>"
                    indexf.WriteLine "</tr>"
            Case Else
                    MsgBox ("In Else" & sName)
         End Select
        
        End If
    Next
        indexf.WriteLine "</table>"
   Next
End Sub

Attribute VB_Name = "frmSelectProduct"
Attribute VB_Base = "0{306286D0-D515-4E01-B14E-5AA991246CDD}{45525FDC-0478-4EAB-A0BA-E4EF31490076}"
Attribute VB_GlobalNameSpace = False
Attribute VB_Creatable = False
Attribute VB_PredeclaredId = True
Attribute VB_Exposed = False
Attribute VB_TemplateDerived = False
Attribute VB_Customizable = False


Option Explicit
'*****************************************************************************
'   frmSelectProduct
'
'                   Hiroyuki Abe(SSE Sumisho Electronics)
'                   Released on 2003/01/09
'
'   更新履歴
'*****************************************************************************
Dim rootProduct As Product   '選択アクティビティ



'*****************************************************************************
' 関数名　 : Private Sub cmdAddPanel_Click()
' 処理概要 : Selectボタン押下時、断面取り対象Obj名称をリストに表示する
' 引数　　 : なし
' 戻り値　 : なし
'*****************************************************************************



Private Sub CommandButton1_Click()

    Dim selcnt As Integer          '選択オブジェクトのカウント

    ' SelectionのObjを取得し、名称を取得する関数呼び出し
    selcnt = GetSelObjName(rootProduct)
    If selcnt = 0 Then
        '無選択であればキャプションを空にして終了
        rootNameParam.Caption = ""
        Exit Sub
    End If
    

    rootNameParam.Caption = rootProduct.Name

End Sub

Private Function GetSelObjName(ByRef outObjA As Product) As Integer

    Dim ActDoc As Document
    Dim SelsDoc
    Dim Cnt As Integer
    Dim st
    Dim trgArray(0)
    Dim selected As Variant
    Dim selcnt As Integer
    trgArray(0) = "Product"
    
    GetSelObjName = 0
    
    ' Selectionを取得
    Set ActDoc = DELMIA.ActiveDocument
    Set SelsDoc = ActDoc.Selection

    selcnt = 0

    If SelsDoc.Count = 1 Then
        Set selected = SelsDoc.Item(1)
        'selected.ValueのクラスはAnyObjectになってしまうのでその親のクラスを取得
        If VBA.TypeName(selected.Value.Parent) = "Products" Then
            Set outObjA = selected.Value
            GetSelObjName = SelsDoc.Count
        Else
            MsgBox "Select element is not a Product."
            Set outObjA = Nothing
            GetSelObjName = 0
        End If
    End If
    SelsDoc.Clear
    
    Set ActDoc = Nothing
    Set SelsDoc = Nothing
    
End Function

Private Sub CommandButton4_Click()
        Dim I As Integer
        Dim tempLineMatrix(11) As Double
        Dim msg As String
        If rootNameParam.Caption <> "" Then
        
        
            If OptionButton1.Value = True Then
                mdlDebugProduct.getPath rootProduct
            End If
            If OptionButton2.Value = True Then
                mdlDebugProduct.getNOS rootProduct
            End If
            If OptionButton3.Value = True Then
                mdlDebugProduct.getHMR rootProduct
            End If
            If OptionButton4.Value = True Then
                mdlDebugProduct.getChildren rootProduct
            End If
            If OptionButton5.Value = True Then
                mdlDebugProduct.getPartNumber rootProduct
            End If
            If OptionButton6.Value = True Then
                mdlDebugProduct.getReferenceProductName rootProduct
            End If
            
            If OptionButton7.Value = True Then
                For I = 0 To 11
                    tempLineMatrix(I) = 0
                Next
                For I = 0 To 2
                    tempLineMatrix(4 * I) = 1#
                Next
                
                msg = ""
                mdlDebugProduct.posFromRoot rootProduct, tempLineMatrix
                
                For I = 0 To 11
                    msg = msg & "mat(" & I & ")= " & tempLineMatrix(I) & vbCrLf
                Next
                
                MsgBox msg
            End If
            
            Unload Me
        Else
            MsgBox "Some parameters is brank. Please input correct parameters"
        End If
        
End Sub

Private Sub CommandButton5_Click()

    Unload Me
End Sub

Private Sub UserForm_Initialize()
    Set rootProduct = Nothing
End Sub
