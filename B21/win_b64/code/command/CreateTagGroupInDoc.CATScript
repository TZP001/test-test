'// ---------- CATIAV5 application objects

'====================================================================================
Sub CATMain() 'Method To create TagGroup in a Process Document
'====================================================================================

Set Parentobject = CATIA.ActiveDocument	
Dim Fact As TagGroupFactory
Set Fact = Parentobject.GetItem("DELMTagGroupFactory")
Dim TagGrp As TagGroup
Fact.CreateTagGroupInDoc "ABC", TagGrp

End Sub '/////////////////////////////////////////////////////////// CATMain
