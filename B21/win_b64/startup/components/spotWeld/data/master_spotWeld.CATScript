'// COPYRIGHT DASSAULT SYSTEMES  1999
'//============================================================================
'//
'// Language="VBSCRIPT"
'// To build catalog
'//
'//============================================================================
'// Major CATIA interface used:
'//
'// interface               VB Name         Remarks
'// -----------            ------------    --------------
'// CATIACatalogDocument   CatalogDocument create catalog
'//
'//============================================================================
'//
'// Audit Trail:
'//----------------------------------------------------------------------------
'//   Author     : Vic Szeto
'//   Date       : 8/99
'//   Chg id     :
'//   Chg nature :
'//----------------------------------------------------------------------------
'//   Modified   : Rex Houdyshel
'//   Date       : 03/00
'//   Chg id     :
'//   Chg nature :
'//============================================================================

Option Explicit

'******************************************************************************
'  GLOBAL variable declarations section
'******************************************************************************
Dim strGInputPath 
Dim strGOutputPath

'@@@@@@@@@@@@@@@@@@@@@@@@@@@@@@@@@@@@@@@@@@@@@@@@@@@@@@@@@@@@@@@@@@@@@@@@@@@@@@
'//                       User customizable sections               
'@@@@@@@@@@@@@@@@@@@@@@@@@@@@@@@@@@@@@@@@@@@@@@@@@@@@@@@@@@@@@@@@@@@@@@@@@@@@@@
Const NBGCSVFile = 5
Dim strArrayGCSVFile (5)

'------------------------------------------------------------------------------
Sub InitCSVFileArray ()
'------------------------------------------------------------------------------

strArrayGCSVFile(1) = "ABB_SpotWeld"
strArrayGCSVFile(2) = "Kuka_SpotWeld"
strArrayGCSVFile(3) = "Nachi_SpotWeld"
strArrayGCSVFile(4) = "Robots_SpotWeld"
strArrayGCSVFile(5) = "Spot_Weld"


End Sub '/////////////////////////////////////////////// InitCSVFileArray

'------------------------------------------------------------------------------
Sub GetPath ()
'------------------------------------------------------------------------------
  strGInputPath = InputBox("Path of the catalog input directory:", _
      "Input path for CSV", _
      "h:\users\s239941\rhl_prjpsl4\CATPlantArrangementUI\CNext\startup\components\spotWeld\data\")

  strGOutputPath = InputBox("Path of the catalog output directory:", _
      "Output path for CSV", _
      "h:\users\s239941\rhl_prjpsl4\CATPlantArrangementUI\CNext\startup\components\spotWeld\")

End Sub '/////////////////////////////////////////////// GetPath
'------------------------------------------------------------------------------
Sub CATMain ()
'------------------------------------------------------------------------------
  Dim objCatalogDoc As Document
  Dim intK As Integer
  Dim strCSVFile
  Dim strCatalogFile

  InitCSVFileArray

  GetPath

  On Error Resume Next

  For intK = 1 to NBGCSVFile
     strCSVFile = strGInputPath & strArrayGCSVFile (intK) & ".csv"
     strCatalogFile = strGOutputPath & strArrayGCSVFile (intK) & ".catalog"
     Set objCatalogDoc = CATIA.Documents.Add("CatalogDocument")

     '---------- Generate catalog
     objCatalogDoc.CreateCatalogFromcsv strCSVFile,strCatalogFile

  Next  'For intK  

  MsgBox "Press OK to quit", 0, "CATALOG CREATION COMPLETED"

End Sub '/////////////////////////////////////////////// CATMain
