'Copyright Dassault Systemes 2002
Language = "VBSCRIPT"

'*****************************************************************************
' Purpose:        Create a "FromTo" wire list for the cable selected in CATIA
' Assumptions:    A cable has been selected in CATIA
'
' Language:       VBScript
' Version:        V5R9
' Reg. Settings:  English (U.S.)
'
'*****************************************************************************
'
' NOTE:
'  Following parameters are language dependent:
'  the value may need to be changed if the language is not English (U.S.)
'-----------------------------------------------------------------------------
TypeName_Cable = "Cable"
TypeName_Equipment = "Equipment"
TypeName_Socket = "Socket"
TypeName_Plug = "Plug"
TypeName_JunctionBox = "Junction"
TypeName_Switch = "Switch"
TypeName_Wire = "Wire"
TypeName_TerminalBoard = "Terminal"
'---------------------------

PathSeparator = "\"
AttrName_ReferenceDesignator = "Reference Designator"
AttrName_Zone = "Electrical zone"

'*****************************************************************************
' Purpose: Make sure that the parameter iProperty is really an attribute of
'          the object, and not an attribute on one of it sub-object.
'          The check is: iProperty.Name contains only
'          one occurence of '/' after the occurence of iObject.Name
' Output:  Return 1 if the parameter is an attribute of the object, and
'          return 0 if the parameter is NOT an attribute of the object.
'*****************************************************************************
'Function IsParameterOf(iProperty As Parameter, iObject as ElecSchematicObject) as Integer
'  On Error Resume Next
'
'  Dim result As Interger
'  Dim inStr1 As Variant
'  Dim inStr2 As Variant
'  Dim inStr3 As Variant
'
'  result = 0
'  inStr1 = InStr(iProperty.Name, iObject.Name)
'  If inStr1 <> 0 Then
'    inStr2 = InStr(inStr1 + Len(iObject.Name), iProperty.Name, PathSeparator)
'    inStr3 = InStr(inStr1 + Len(iObject.Name) + 1, iProperty.Name, PathSeparator)
'    If inStr2 <> 0 AND inStr3 = 0 then
'      result = 1
'    End If
'  End If
'  IsParameterOf = result
'End Function


'*****************************************************************************
' Purpose: Get the NLS name of a property, for the given object.
' Example 1:
'   If iProperty.Name equals to "System1\Cable1.1\Reference Designator"
'   and iObject.Name equals to "Cable1.1", then returns "Reference Designator".
' Example 2:
'   If iProperty.Name equals to "System1\Cable1.1\Reference Designator"
'   and iObject.Name equals to "Wire1.1", then returns "".
'*****************************************************************************
Function GetAttributeName(iProperty As Parameter, iObject As ElecSchematicObject) As String
  Dim result As String
  Dim inStr1 As Variant 'index of 1st occurence of iObject.Name within iProperty.Name
  Dim inStr2 As Variant 'index of last occurence of "\" within iProperty.Name
  Dim inStr3 As Variant
  
  GetAttributeName = ""

  inStr1 = InStr(iProperty.Name, iObject.Name)
  If inStr1 <> 0 Then
    inStr2 = InStr(inStr1 + Len(iObject.Name), iProperty.Name, PathSeparator)
    inStr3 = InStr(inStr1 + Len(iObject.Name) + 1, iProperty.Name, PathSeparator)
    If inStr2 <> 0 And inStr3 = 0 Then
      GetAttributeName = Mid(iProperty.Name, inStr2 + 1)
    End If
  End If
End Function


'*****************************************************************************
' Purpose: Get the value for the specified attribute.
' Inputs:  iAttributeName:  the NLS name (language dependent) of the attibute
'          iObject:         the attribute holder
'*****************************************************************************
Function GetAttributeValue(iAttributeName As String, iObject As ElecSchematicObject) As String
  On Error Resume Next
  GetAttributeValue = "" 'in order to return empty string in case of error

  if Not(iObject is Nothing) then
    
    If (InStr (iAttributeName,AttrName_ReferenceDesignator) <> 0) then
       GetAttributeValue = iObject.PartNumber
       Exit Function
    End If

    'GetAttributeValue = iObject.Parameters.Item(iObject.Name & PathSeparator & iAttributeName).ValueAsString
    Dim Properties2 As Parameters
    Dim Property2 As Parameter
    Set Properties2 = iObject.Parameters
    For i2=1 To Properties2.Count
      Set Property2 = Properties2.Item(i2)
      if (InStr(Property2.Name,iObject.Name & PathSeparator & iAttributeName)) <> 0 Then
        GetAttributeValue = Property2.ValueAsString '& " @ "&Property.Name
      End If
    Next

    If Not(iObject.ElecSchematicParent is Nothing) then
      If (InStr(iObject.RootType, TypeName_Wire) <> 0) then
        Dim Properties As Parameters
        Dim Property As Parameter
        Set Properties = iObject.Parameters
        For i=1 To Properties.Count
          Set Property = Properties.Item(i)
          if (InStr(Property.Name,iObject.ElecSchematicParent.Name & PathSeparator & iObject.Name & PathSeparator & iAttributeName)) <> 0 Then
            'if GetAttributeName(Property,iObject) <> "" Then
              GetAttributeValue = Property.ValueAsString '& " @ "&Property.Name
            '  Exit Function
            'End If
          End If
        Next
      End If
    End If
  End If

  'On Error Goto 0
End Function


'*****************************************************************************
' Purpose: Get the unit (equipment or junction box) which is connected or
'          which is the parent of the specified object.
' Input:
'   iElecObject:   an electrical component (equipment, terminal board,
'                  plug, socket, junction box)
' Output:
'   If the input is a piece of equipment, then returns it.
'   If the input is a junction box, then returns it.
'   If the input is a socket, then returns the parent equipment.
'   If the input is a plug, then returns the corresponding equipment (if any).
'   If the input is a terminal board, then returns the parent junction box.
'*****************************************************************************
Function GetUnitFromComponent(iElecObject As ElecSchematicObject) As ElecSchematicObject
  If (InStr(iElecObject.RootType, TypeName_Equipment)) <> 0 Then
    Set GetUnitFromComponent = iElecObject
  ElseIf (InStr(iElecObject.RootType, TypeName_JunctionBox)) <> 0 Then
    Set GetUnitFromComponent = iElecObject
  ElseIf (InStr(iElecObject.RootType, TypeName_Switch)) <> 0 Then
    Set GetUnitFromComponent = iElecObject
  ElseIf (InStr(iElecObject.RootType, TypeName_Socket)) <> 0 Then
    Set GetUnitFromComponent = iElecObject.ElecSchematicParent
  ElseIf (InStr(iElecObject.RootType, TypeName_Plug)) <> 0 Then
    Dim ObjectsConnectedToPlug As SchListOfObjects
    Set ObjectsConnectedToPlug = iElecObject.ConnectedElecSchObjects
    If Not (ObjectsConnectedToPlug Is Nothing) Then
      Dim CurrentItem As ElecSchematicObject
      For idY = 1 To ObjectsConnectedToPlug.Count
        Set CurrentItem = ObjectsConnectedToPlug.Item(idY,"CATIAElecSchematicObject")
        If (InStr(CurrentItem.RootType, TypeName_Socket)) <> 0 Then
          Set GetUnitFromComponent = CurrentItem.ElecSchematicParent
        End If
      Next
    End If
  ElseIf (InStr(iElecObject.RootType, TypeName_TerminalBoard)) <> 0 Then
    Set GetUnitFromComponent = iElecObject.ElecSchematicParent
  End If
End Function



'*****************************************************************************
' Purpose: Get the ID of the pin which connects the specified device and wire.
'*****************************************************************************
Function GetPinID(iElecDevice As ElecSchematicObject, iElecWire As ElecSchematicObject) As String
  On Error Resume Next
  If Not(iElecDevice is Nothing) then
    GetPinID = iElecDevice.GetPinAttribute(iElecWire, "Elec_Id_Number")
  Else
    GetPinID = ""
  End If
  'On Error Goto 0
End Function


'*****************************************************************************
' Purpose: Reduce or increase the length of the input string, in order to get
'          a new string whose length in the specified one.
'*****************************************************************************
Function ResizeString(iString as String, iLength as Integer) As String
  if (Len(iString) >= iLength) then
    ResizeString = Left (iString, iLength)
  else
    ResizeString = Left (iString & "                                                                                ", iLength)
  end if
End Function


'*****************************************************************************
'
' MainSub of the script
'
'*****************************************************************************
Sub CATMain()
  On Error Resume Next

  ' Open the product
  ' ================
  Dim ProductDoc As ProductDocument
  Set ProductDoc = CATIA.ActiveDocument

  ' Get the file system object
  ' ==========================
  Dim oFileSys As FileSystem
  Set oFileSys = CATIA.FileSystem

  ' Create file for the report
  ' ==========================
  Dim sMessage As String
  sMessage = InputBox("Enter the report filename", "Schematic Report", "h:\ReportFromToList.txt")
  If sMessage = "" Then
    Exit Sub
  End If

  Dim oFilIn As File
  Set oFilIn = oFileSys.CreateFile(sMessage, False)
  Dim oStream As TextStream
  Set oStream = oFilIn.OpenAsTextStream("ForWriting")


  ' Declare some global variables
  ' =============================
  Dim CurrentCable As ElecSchematicObject    'The cable which is currently computed
  Dim CurrentFromUnit As ElecSchematicObject 'An 1st equipment/junction box/switch connected to the cable
  Dim CurrentToUnit As ElecSchematicObject   'An 2nd equipment/junction box/switch connected to the cable
  Dim CurrentFromBoard As ElecSchematicObject 'An 1st plug/socket/switch connected to the cable
  Dim CurrentToBoard As ElecSchematicObject   'An 2nd equipment/junction box/switch connected to the cable

  Dim Properties As Parameters
  Dim Property As Parameter
  Dim PropertyName As String

  Dim IsGenerated As Boolean
  IsGenerated = False

  ' Loop on selected cable(s)
  ' =========================
  Do
    Set CurrentCable = Nothing
    'On Error Resume Next
    Set CurrentCable = ProductDoc.Selection.FindObject("CATIAElecSchematicObject")
    'On Error Goto 0


    ' No report is generated if the current object is empty
    ' =====================================================
    If CurrentCable Is Nothing Then
      'CATIA.SystemService.Print "No CATIAElecSchematicObject found ***"
      Exit Do
    End If     

    ' No report is generated if the current object is not a cable.
    ' ====================================================================
    '-If (InStr(CurrentCable.RootType, TypeName_Cable)) = 0 Then
      'MsgBox "One or several cable(s) must be selected before the report is generated.", vbOKOnly & vbInformation, "Schematic Report"
      '-Exit Do
    '-End If

    If (InStr(CurrentCable.RootType, TypeName_Cable)) > 0 Then

    oStream.Write "-------------------------------------------------------------------------------" & vbCrLf & vbCrLf
    IsGenerated = True


    ' Display cable's attributes
    ' ==========================
    oStream.Write "Circuit number = " & GetAttributeValue(AttrName_ReferenceDesignator, CurrentCable) & vbCrLf
    oStream.Write "Cable Type = " & CurrentCable.Type & vbCrLf
    oStream.Write "Cable Instance Name = " & CurrentCable.Name & vbCrLf

    Set Properties = CurrentCable.Parameters
    For i = 1 To Properties.Count
      Set Property = Properties.Item(i)
      PropertyName = GetAttributeName(Property, CurrentCable)
      If PropertyName <> "" Then
        oStream.Write "   " & PropertyName & " = " & Property.ValueAsString & vbCrLf
      End If
    Next
    oStream.Write vbCrLf & vbCrLf

    ' Get units (equipment/junction box) connected to the current cable
    ' =================================================================
    oStream.Write vbCrLf & "Units connected to the cable" & vbCrLf
    oStream.Write "-------------------------------------------------------------------------------" & vbCrLf
    Dim ConnectedObjects As SchListOfObjects
    Set ConnectedObjects = CurrentCable.ConnectedElecSchObjects

    If Not (ConnectedObjects Is Nothing) Then

      'CATIA.SystemService.Print "Number of connected objects = " & ConnectedObjects.Count

      ' Get the units
      ' =============
      If (ConnectedObjects.Count = 1) Then
        Set CurrentFromUnit = GetUnitFromComponent(ConnectedObjects.Item(1,"CATIAElecSchematicObject"))
        Set CurrentToUnit = Nothing
      ElseIf (ConnectedObjects.Count = 2) Then
        Set CurrentFromUnit = GetUnitFromComponent(ConnectedObjects.Item(1,"CATIAElecSchematicObject"))
        Set CurrentToUnit = GetUnitFromComponent(ConnectedObjects.Item(2,"CATIAElecSchematicObject"))
      End If

      ' Display the units (components)
      ' ==============================
      If (Not (CurrentFromUnit Is Nothing) AND Not (CurrentToUnit Is Nothing)) Then
        oStream.Write ResizeString (" Unit A: " & CurrentFromUnit.Name, 39) & "|"
        oStream.Write ResizeString (" Unit B: " & CurrentToUnit.Name, 39) & vbCrLf
        'oStream.Write ResizeString (" Unit A: " & GetAttributeValue(AttrName_ReferenceDesignator, CurrentFromUnit), 39) & "|"
        'oStream.Write ResizeString (" Unit B: " & GetAttributeValue(AttrName_ReferenceDesignator, CurrentToUnit), 39) & vbCrLf
        'oStream.Write ResizeString ("   Name: " & CurrentFromUnit.Name, 39) & "|"
        'oStream.Write ResizeString ("   Name: " & CurrentToUnit.Name, 39) & vbCrLf
        oStream.Write ResizeString ("   Type: " & CurrentFromUnit.Type, 39) & "|"
        oStream.Write ResizeString ("   Type: " & CurrentToUnit.Type, 39) & vbCrLf
        oStream.Write ResizeString ("   PartNumber: " & CurrentFromUnit.PartNumber, 39) & "|"
        oStream.Write ResizeString ("   PartNumber: " & CurrentToUnit.PartNumber, 39) & vbCrLf
        oStream.Write ResizeString ("   Zone: " & GetAttributeValue(AttrName_Zone,CurrentFromUnit), 39) & "|"
        oStream.Write ResizeString ("   Zone: " & GetAttributeValue(AttrName_Zone,CurrentToUnit), 39) & vbCrLf
      ElseIf Not (CurrentFromUnit Is Nothing) Then
        oStream.Write ResizeString (" Unit A: " & CurrentFromUnit.Name, 39) & vbCrLf
        'oStream.Write " Unit A: " & GetAttributeValue(AttrName_ReferenceDesignator, CurrentFromUnit) & vbCrLf
        'oStream.Write "   Name = " & CurrentFromUnit.Name & vbCrLf
        oStream.Write "   RootType = " & CurrentFromUnit.RootType & vbCrLf
        oStream.Write "   Type = " & CurrentFromUnit.Type & vbCrLf
        oStream.Write "   PartNumber = " & CurrentFromUnit.PartNumber & vbCrLf
        Set Properties = CurrentFromUnit.Parameters
        For i = 1 To Properties.Count
          Set Property = Properties.Item(i)
          PropertyName = GetAttributeName(Property, CurrentFromUnit)
          If PropertyName <> "" Then
            oStream.Write "   " & PropertyName & " = " & Property.ValueAsString & vbCrLf
          End If
        Next
      End If
    End If
    oStream.Write "-------------------------------------------------------------------------------" & vbCrLf & vbCrLf


    ' Display the FromTo list itself (loop on wires)
    ' ==============================================
    Dim CableChildren As SchListOfObjects
    Dim objWire As ElecSchWire
    Dim strColor As String
    Dim strWireID As String
    Set CableChildren = CurrentCable.ElecSchematicChildren
    If Not (CableChildren Is Nothing) Then
      oStream.Write vbCrLf & "List of wires, with connected terminals" &vbCrLf
      oStream.Write "------------------------------------------------------------------------------------" & vbCrLf
      oStream.Write " Unit | Terminal                | Wire                | color | Unit | Terminal                 " & vbCrLf
      oStream.Write "------------------------------------------------------------------------------------" & vbCrLf
      ' Loop on the wires
      ' =================
      Dim CurrentChild As ElecSchematicObject
      For i = 1 To CableChildren.Count
        Set CurrentChild = CableChildren.Item(i,"CATIAElecSchematicObject")

        If (InStr(CurrentChild.RootType, TypeName_Wire)) <> 0 Then
          Dim ConnectedToWire As SchListOfObjects
          Set ConnectedToWire = CurrentChild.ConnectedElecSchObjects

          'Gets the boards connected to the wire
          Set CurrentFromBoard = Nothing
          Set CurrentToBoard = Nothing
          If (ConnectedToWire.Count = 1) Then
            Set CurrentFromBoard = ConnectedToWire.Item(1,"CATIAElecSchematicObject")
          ElseIf (ConnectedToWire.Count = 2) Then
            Set CurrentFromBoard = ConnectedToWire.Item(1,"CATIAElecSchematicObject")
            Set CurrentToBoard = ConnectedToWire.Item(2,"CATIAElecSchematicObject")
          End If
          
          'Swap FromTo boards if necessary
          If (Not (CurrentFromBoard Is Nothing) And Not (GetUnitFromComponent(CurrentFromBoard) Is Nothing)) Then
            If (StrComp(GetUnitFromComponent(CurrentFromBoard).Name, CurrentFromUnit.Name) <> 0) Then
              Dim tempo As ElecSchematicObject
              Set tempo = CurrentFromBoard
              Set CurrentFromBoard = Nothing
              
              'On Error Resume Next
              Set CurrentFromBoard = CurrentToBoard
              'On Error Goto 0

              Set CurrentToBoard = tempo
            End If
          End If
          

          Dim fromPinId
          Dim toPinId
          fromPinId = PathSeparator & GetPinID(CurrentFromBoard, CurrentChild)
          toPinId = PathSeparator & GetPinID(CurrentToBoard, CurrentChild)

          strWireID = GetAttributeValue(AttrName_ReferenceDesignator, CurrentChild)
          strColor = ""
          Set objWire = CurrentChild.GetTechnologicalObject (strColor)
          If ( Not ( objWire Is Nothing ) ) Then
             strColor = objWire.Color
          End If          

          oStream.Write " " & ResizeString("A",5) & "| " 
          oStream.Write ResizeString(GetAttributeValue(AttrName_ReferenceDesignator, CurrentFromBoard)&fromPinId,24) & "| "
          oStream.Write ResizeString(strWireID,20) & "| " 
          oStream.Write ResizeString(strColor,5) & " | "
          oStream.Write ResizeString("B",5) & "| " 
          oStream.Write ResizeString(GetAttributeValue(AttrName_ReferenceDesignator, CurrentToBoard)&toPinId,24) & vbCrLf

        End If

      Next
    End If

      oStream.Write "------------------------------------------------------------------------------------" & vbCrLf & vbCrLf

    'Else
     'CATIA.SystemService.Print "not a cable ************* " & CurrentCable.Name
    End If '(InStr(CurrentCable.RootType, TypeName_Cable)) > 0
    '-------------------------------------------------------------------

  Loop

  If IsGenerated = True Then
    'MsgBox "The report has been generated !", vbOKOnly & vbInformation, "Schematic Report"
  End If
End Sub
